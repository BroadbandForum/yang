submodule bbf-fast-fast-rate-adaptation-profile-body {
  yang-version 1.1;
  belongs-to bbf-fast {
    prefix bbf-fast;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing Fast Rate Adaptation (FRA) profiles.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping fast-rate-adaptation-parameters {
    description
      "Fast Rate Adaptation (FRA) configuration parameters
       applicable to both upstream and downstream.";
    reference
      "ITU-T G.997.2 clause 7.1.5";
    leaf time-window {
      type uint8 {
        range "0 | 1..36";
      }
      units "logical frame periods";
      default "8";
      description
        "Defines the duration of the time window used in the standard
         Fast Rate Adaptation (FRA) triggering criteria. The special
         value, 0, indicates that the vendor discretionary values
         for fra-ntones, fra-rtx-uc, and fra-time may be used.";
      reference
        "ITU-T G.997.2 clause 7.1.5.1 (FRA-TIMEds) and clause
         7.1.5.2 (FRA-TIMEus);
         ITU-T G.9701 clause 13.3.1.1.1.1";
    }
    leaf minimum-degraded-tones {
      type uint8 {
        range "0 | 1..100";
      }
      units "percent";
      default "50";
      description
        "Defines the minimum percentage of loaded sub-carriers (i.e.
         sub-carriers with bi>0) that are detected as degraded
         throughout a time window equal to FRA-TIME in order to arm
         the first Fast Rate Adaptation (FRA) triggering criteria.
         The special value, 0, indicates that monitoring of the
         percentage of degraded sub-carriers is disabled.";
      reference
        "ITU-T G.997.2 clause 7.1.5.3 (FRA-NTONESds) and clause
         7.1.5.4 (FRA-NTONESus);
         ITU-T G.9701 clause 13.3.1.1.1.2";
    }
    leaf uncorrectable-dtu {
      type uint16 {
        range "0 | 1..1023";
      }
      default "150";
      description
        "Defines the minimum number of rtx-uc anomalies received
         throughout a time window equal to FRA-TIME in order to arm
         the second Fast Rate Adaptation (FRA) triggering criteria.
         The special value, 0, indicates that monitoring of the
         number of rtx-uc anomalies is disabled.";
      reference
        "ITU-T G.997.2 clause 7.1.5.5 (FRA-RTXUCds) and clause
         7.1.5.6 (FRA-RTXUCus);
         ITU-T G.9701 clause 13.3.1.1.1.3";
    }
    leaf vendor-discretionary-fra-triggering-criteria {
      type boolean;
      default "false";
      description
        "Defines whether vendor discretionary Fast Rate Adaptation
         (FRA) triggering criteria may be used (enabled) or not
         (disabled).";
      reference
        "ITU-T G.997.2 clause 7.1.5.7 (FRA-VENDISds) and clause
         7.1.5.8 (FRA-VENDISus);
         ITU-T G.9701 clause 13.3.1.1.1.4";
    }
  }

  grouping fast-rate-adaptation-profile {
    description
      "Defines the contents of a Fast Rate Adaptation (FRA) Profile.";
    container downstream {
      description
        "Downstream Fast Rate Adaptation (FRA) profile.";
      uses fast-rate-adaptation-parameters;
    }
    container upstream {
      description
        "Upstream Fast Rate Adaptation (FRA) profile.";
      uses fast-rate-adaptation-parameters;
    }
  }
}
