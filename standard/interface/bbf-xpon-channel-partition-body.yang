submodule bbf-xpon-channel-partition-body {
  yang-version 1.1;
  belongs-to bbf-xpon {
    prefix bbf-xpon;
  }

  import ietf-interfaces {
    prefix if;
  }
  import bbf-xpon-if-type {
    prefix bbf-xponift;
  }
  import bbf-xpon-types {
    prefix bbf-xpon-types;
  }
  include bbf-xpon-base;

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This submodule contains a collection of YANG definitions for
     managing channel partitions.

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }
  revision 2024-04-23 {
    description
      "Issue 3.
       * Approval Date:    2024-04-23.
       * Publication Date: 2024-04-23.";
    reference
      "TR-385i3: YANG Modules for PON Management
               <https://www.broadband-forum.org/technical/download/
                        TR-385_Issue-3.pdf>";
  }
  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }
  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }
  revision 2019-02-25 {
    description
      "Initial revision.
       * Approval Date:    2019-02-25.
       * Publication Date: 2019-02-25.";
    reference
      "TR-385: ITU-T PON YANG Modules
               <https://www.broadband-forum.org/technical/download/
                        TR-385.pdf>";
  }

  grouping channel-partition-config-data {
    description
      "All configuration data for a channel partition.";
    leaf channel-group-ref {
      type if:interface-ref;
      must "derived-from-or-self(/if:interfaces"
         + "/if:interface[if:name=current()]/if:type,"
         + "'bbf-xponift:channel-group')" {
        error-message "Must reference a channel group.";
      }
      mandatory true;
      description
        "Reference to a channel group.";
    }
    leaf channel-partition-index {
      type uint8 {
        range "0..15";
      }
      description
        "Identifies the partition inside the channel group.";
      reference
        "ITU-T G.989.3 Clause 6.1.5.9;
         ITU-T G.989.3 Clause 11.3.3.14";
    }
    leaf downstream-fec {
      type boolean;
      default "true";
      description
        "If 'true', enables downstream Forward Error Correction (FEC).
         Note that downstream FEC is always enabled for XG-PON,
         XGS-PON, 50G-PON and 25GS-PON and thus a value of 'false' is
         ignored.";
      reference
        "ITU-T G.984.3 Clause 13.1.2.1;
         ITU-T G.987.3 Clause 10.3;
         ITU-T G.9807.1 Clause C.10.1.3.1.2;
         ITU-T G.989.3 Clause 10.1.3.1.2;
         ITU-T G.9804.2 Clause 10.3.1.2;
         MSA 25GS-PON Section C.10.1.3.1.1";
    }
    leaf downstream-interleaving {
      type boolean;
      default "false";
      description
        "If 'true', enables downstream interleaving mode. This is only
         applicable for 50G-PON (ITU-T G.9804.2). The configuration is
         ignored for G-PON, XG-PON, XGS-PON, and 25GS-PON.";
      reference
        "ITU-T G.9804.2 Clause 10.5";
    }
    leaf closest-onu-distance {
      type uint16 {
        range "0..40";
      }
      units "kilometers";
      default "0";
      description
        "Establishes the distance of the closest Optical Network Unit
         (ONU). Used to determine how to equalize delay between the
         ONUs.";
    }
    leaf maximum-differential-xpon-distance {
      type uint16 {
        range "20 | 40";
      }
      units "kilometers";
      default "20";
      description
        "Provides the ability to set the maximum differential logical
         reach for a channel partition.";
      reference
        "ITU-T G.989.1 Clause 8.2;
         ITU-T G.989.3 Clause 13.1";
    }
    leaf authentication-method {
      type bbf-xpon-types:auth-method-type;
      default "serial-number";
      description
        "Optical Network Unit (ONU) Authentication mode option for
         this channel partition.";
      reference
        "ITU-T G.984.3, Clause VI.1";
    }
    leaf multicast-aes-indicator {
      type boolean;
      default "false";
      description
        "If 'true', enables Advanced Encryption Standard (AES) for
         multicast G-PON Encapsulation Method (GEM) ports.";
      reference
        "ITU-T G.984.3 Clause 12.2;
         ITU-T G.984.3 Clause 9.2.3.8;
         ITU-T G.987.3 Clause 15.5.1;
         ITU-T G.987.3 Clause 15.5.4;
         ITU-T G.9807.1 Clause C.15.5.1;
         ITU-T G.9807.1 Clause C.15.5.4;
         ITU-T G.989.3 Clause 15.5.1;
         ITU-T G.989.3 Clause 15.5.4;
         ITU-T G.9804.2 Clause 15.5.1;
         ITU-T G.9804.2 Clause 15.5.4";
    }
  }

  augment "/if:interfaces/if:interface/bbf-xpon:channel-partition" {
    description
      "Configuration of an xPON channel partition.";
    uses channel-partition-config-data;
  }
}
