submodule bbf-selt-processing-profile-body {
  yang-version 1.1;
  belongs-to bbf-selt {
    prefix bbf-selt;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing processing profiles.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping downstream-upstream-parameters {
    description
      "Parameters to define the configuration common between the
       downstream and upstream directions.";
    container capacity-estimate-signal-psd {
      list psd {
        key "t";
        max-elements 48;
        description
          "A list of Power Spectral Density (PSD) values per
           breakpoint, t.";
        leaf t {
          type uint16 {
            range "0..8191";
          }
          description
            "The breakpoint index.";
        }
        leaf psd {
          type int16 {
            range "-2000..-300" {
              description
                "Defines a range from -200.0 to 30.0 dBm per Hz.";
            }
          }
          units "0.1 dBm per Hz";
          mandatory true;
          description
            "The Power Spectral Density (PSD) value.";
        }
      }
      description
        "This configuration parameter defines the Power Spectral
         Density (PSD) template of the transmit signal to be used in
         capacity estimate evaluation. The PSD template CAP-SIGNALPSD
         shall be specified through a set of breakpoints. Each
         breakpoint shall consist of a frequency index, tn, and a
         signal PSD level (expressed in dBm/Hz). The parameter shall
         be a set of breakpoints represented by [(t1, PSD1),
         (t2, PSD2), ..., (tN, PSDN)], where t1 and tN represent,
         respectively, the lower frequency of the lowest band over
         which the capacity estimate is to be calculated, and the
         highest frequency of highest band over which the capacity
         estimate is to be calculated. In the case of an estimation of
         capacity for a multi-band xDSL, the set of breakpoints shall
         describe the stopbands situated inbetween passbands.

         NOTE - Stopbands may be described as brickwall stopbands
                using the lowest valid value (-200 dBm/Hz) or may be
                described more elaborately.

         The breakpoints shall be defined so that tn < tn+1 for n = 1
         to N - 1. The frequency fn corresponding to the index tn can
         be found as: fn = tn * Df. The value of Df = 4.3125 kHz and
         is independent of the subcarrier spacing used for the DMT
         modulation of the xDSL.

         The range of valid values for index tn is 0 to 8191 in steps
         of 1. The range of valid values for PSD is -30 to -200
         dBm per Hz in steps of 0.1 dBm per Hz.";
      reference
        "ITU-T G.996.2 clause B.2.1.2 (CAP-SIGNALPSD)";
    }
    container capacity-estimate-noise-psd {
      list psd {
        key "t";
        max-elements 128;
        description
          "A list of Power Spectral Density (PSD) values per
           breakpoint, t.";
        leaf t {
          type uint16 {
            range "0..8191";
          }
          description
            "The breakpoint index.";
        }
        leaf psd {
          type int16 {
            range "-2000..-30" {
              description
                "Defines a range from -200.0 to 30.0 dBm per Hz.";
            }
          }
          units "0.1 dBm per Hz";
          mandatory true;
          description
            "The Power Spectral Density (PSD) value.";
        }
      }
      description
        "This configuration parameter defines the Power Spectral
         Density (PSD) template of the received noise to be used in
         capacity estimate evaluation. The PSD template CAP-NOISEPSD
         shall be specified through a set of breakpoints. Each
         breakpoint shall consist of a frequency index tn and a signal
         PSD level (expressed in dBm/Hz). The parameter shall be a set
         of breakpoints that are represented by [(t1, PSD1),
         (t2, PSD2), ... ,(tN, PSDN)], where t1 and tN are,
         respectively, the lower frequency of the lowest band over
         which the capacity estimate is to be calculated, and the
         highest frequency of highest band over which the capacity
         estimate is to be calculated.

         In the case of an estimation of capacity for a multi-band
         xDSL, with the CAP-SIGNALPSD stopbands described as
         brickwall stopbands, the set of breakpoints for CAP-NOISEPSD
         is not required to describe the noise in the stopbands
         situated inbetween passbands. In case the CAP-SIGNALPSD
         stopbands are not described as brickwall stopbands, the set
         of breakpoints for CAP-NOISEPSD shall describe the noise in
         the stopbands situated inbetween passbands. The breakpoints
         shall be defined so that tn < tn+1 for n = 1 to N - 1. The
         frequency fn corresponding to the index tn can be found as:
         fn = tn * Df. The value of Df = 4.3125 kHz and is
         independent of the subcarrier spacing used for the DMT
         modulation of the xDSL.

         The range of valid values for index tn is 0 to 8191, in
         steps of 1. The range of valid values for PSD is -30 to -200
         dBm per Hz, in steps of 0.1 dBm per Hz.";
      reference
        "ITU-T G.996.2 clause B.2.1.3 (CAP-NOISEPSD)";
    }
    leaf capacity-estimate-target-noise-margin {
      type uint16 {
        range "0..310" {
          description
            "Defines a range from 0.0 to 31.0 dB.";
        }
      }
      units "0.1 dB";
      description
        "This is the noise margin to be used in capacity estimate
         evaluation, relative to a Bit Error Rate (BER) requirement
         of 1E-7.

         The range of valid values for CAP-TARSNRM expressed in dB is
         0 to 31 dB, in steps of 0.1 dB.";
      reference
        "ITU-T G.996.2 clause B.2.1.4 (CAP-TARSNRM)";
    }
  }

  grouping processing-profile {
    description
      "Defines the parameters contained in a processing profile.";
    leaf capacity-estimate-calculation-enabling {
      type boolean;
      description
        "This parameter specifies if the Single Ended Line Test
         Processing (SELT-P) function shall perform the 'downstream
         capacity' and 'upstream capacity' estimations, if supported.
         This parameter is expressed as a boolean flag and takes the
         value 'false' if xDSL performance estimation is not required,
         true otherwise.";
      reference
        "ITU-T G.996.2 clause B.2.1.1 (CECE)";
    }
    container downstream {
      description
        "Data nodes applicable in the downstream direction.";
      uses downstream-upstream-parameters;
    }
    container upstream {
      description
        "Data nodes applicable in the upstream direction.";
      uses downstream-upstream-parameters;
    }
  }
}
