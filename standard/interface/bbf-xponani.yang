module bbf-xponani {
  yang-version 1.1;
  namespace "urn:bbf:yang:bbf-xponani";
  prefix bbf-xponani;

  import ietf-interfaces {
    prefix if;
  }
  import bbf-xpon-types {
    prefix bbf-xpon-types;
  }
  import bbf-xpon-if-type {
    prefix bbf-xponift;
  }
  import bbf-xponani-common {
    prefix bbf-xponanic;
  }

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on the management of
     Passive Optical Network (PON) interfaces. As such, this module
     is specific to access network equipment (e.g., BBF-specified
     Access Nodes and FTTdp DPUs).

     Specifically, this module defines management of Access Network
     Interfaces (ANI) which represent the physical Optical Network
     Unit (ONU).

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }
  revision 2024-04-23 {
    description
      "Issue 3.
       * Approval Date:    2024-04-23.
       * Publication Date: 2024-04-23.";
    reference
      "TR-385i3: YANG Modules for PON Management
               <https://www.broadband-forum.org/technical/download/
                        TR-385_Issue-3.pdf>";
  }
  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }
  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }
  revision 2019-02-25 {
    description
      "Initial revision.
       * Approval Date:    2019-02-25.
       * Publication Date: 2019-02-25.";
    reference
      "TR-385: ITU-T PON YANG Modules
               <https://www.broadband-forum.org/technical/download/
                        TR-385.pdf>";
  }

  feature configurable-ani-onu-id {
    description
      "Indicates support for configuration of the Optical Network Unit
       (ONU) ID associated with the Access Network Interface (ANI).";
  }

  feature configurable-ani-management-gem-port-id {
    description
      "Indicates support for configuration of the management G-PON
       Encapsulation Method (GEM) port.";
  }

  feature ani-onu-serial-number-reporting {
    description
      "Indicates that the Access Network Interface (ANI) holds the
       Optical Network Unit (ONU) serial number in its state data.";
  }

  feature ani-defects {
    description
      "Indicates support for reporting defects observed at the Access
       Network Interface (ANI).";
  }

  feature ani-defect-notifications {
    description
      "Indicates support for reporting state change of the defects
       observed at the Access Network Interface (ANI).";
  }

  augment "/if:interfaces/if:interface" {
    when "derived-from-or-self(if:type, 'bbf-xponift:ani')";
    description
      "Augment interface configuration with xPON Access Newtork
       Interface (ANI) configuration.

       The ANI represents the Optical Network Unit (ONU) device.";
    container ani {
      description
        "ANI configuration.";
      uses bbf-xponanic:ani-config-data {
        refine "upstream-fec" {
          default "false";
        }
        refine "management-gemport-aes-indicator" {
          default "false";
        }
        refine "notifiable-defect" {
          if-feature "bbf-xponani:ani-defect-notifications";
        }
      }
      leaf onu-id {
        if-feature "bbf-xponani:configurable-ani-onu-id";
        type bbf-xpon-types:onu-id;
        description
          "The TC layer ONU Identifier (ONU-ID). When configured this
           is the value which the Optical Line Termination (OLT) must
           assign to the Optical Network Unit (ONU) during the ONU's
           activation using the Assign_ONU-ID Physical Layer
           Operations, Administrations and Maintenance (PLOAM)
           message.

           For G-PON, range is 0..253.
           For XG-PON, range is 0..1022.
           For XGS-PON, range is 0..1020.
           For NG-PON2, range is 0..1020.
           For 25GS-PON, range is 0..1018.
           For 50G-PON, range is 0..1019.";
        reference
          "ITU-T G.984.3 Clause 5.5.2;
           ITU-T G.987.3 Clause 6.4.2;
           ITU-T G.9807.1 Clause C.6.1.5.6;
           ITU-T G.989.3 Clause 6.1.5.6;
           ITU-T G.9804.2 Clause 6.5.2.5;
           MSA 25GS-PON Section C.6.1.5.7";
      }
      leaf management-gemport-id {
        if-feature "bbf-xponani:"
                 + "configurable-ani-management-gem-port-id";
        type uint32;
        description
          "This leaf is only relevant to G-PON ONUs; it is ignored for
           non-G-PON ONUs. In contrast with other xPON technologies,
           in the case of G-PON, there is no requirement that the
           ITU-T TC ID of the management G-PON Encapsulation Method
           (GEM) port for the Optical Network Unit (ONU) is
           numerically equal to the ONU-ID. This leaf provides the
           capability to specify value for the management GEM port ID.

           If this leaf is not configured the management GEM port
           ID must be numerically equal to the ONU-ID.";
        reference
          "ITU-T G.984.3 Clause 5.5.5 - OMCC Port-ID;
           ITU-T G.987.3 Clause 6.4.4 - OMCC Port-ID;
           ITU-T G.989.3 Clause 6.1.5.8 - OMCC Port-ID;
           ITU-T G.9807.1 Clause C.6.1.5.8 - OMCC Port-ID;
           ITU-T G.9804.2 Clause 6.5.2.7 - OMCC Port-ID";
      }
    }
  }

  augment "/if:interfaces-state/if:interface" {
    when "derived-from-or-self(if:type, 'bbf-xponift:ani')";
    description
      "Augment interface state data with xPON Access Network Interface
       (ANI) state data.

       The ANI represents the Optical Network Unit (ONU) device.";
    container ani {
      config false;
      description
        "State data for ANI interface.";
      uses bbf-xponanic:ani-state-data {
        refine "onu-serial-number" {
          if-feature "bbf-xponani:ani-onu-serial-number-reporting";
        }
        refine "active-defects" {
          if-feature "bbf-xponani:ani-defects";
        }
      }
    }
  }

  augment "/if:interfaces/if:interface" {
    when "derived-from-or-self(if:type, 'bbf-xponift:onu-v-enet')";
    description
      "Augment interface configuration with xPON Optical Network Unit
       (ONU) virtual ENET interface configuration.";
    container onu-v-enet {
      description
        "ONU virtual ENET configuration.";
      leaf ani {
        type if:interface-ref;
        must "derived-from-or-self(/if:interfaces"
           + "/if:interface[if:name = current()]/if:type,"
           + "'bbf-xponift:ani')" {
          error-message
            "The referenced interface is not of type or derived from "
          + "type 'bbf-xponift:ani'.";
          description
            "The referenced interface must be of or derived from type
             'bbf-xponift:ani'.";
        }
        mandatory true;
        description
          "References the Access Network Interface (ANI) which is the
           lower-layer interface under the ONU-vENET.";
      }
    }
  }

  augment "/if:interfaces/if:interface" {
    when "derived-from-or-self"
       + "(if:type,'bbf-xponift:onu-v-vrefpoint')";
    description
      "Augment interface configuration with xPON virtual V reference
       point interface per TR-167 (sometimes also called 'virtual User
       Network Interface (UNI)').";
    container onu-v-vrefpoint {
      description
        "Virtual User Network Interface (UNI) configuration.";
      leaf related-onu {
        type if:interface-ref;
        must "derived-from-or-self(/if:interfaces"
           + "/if:interface[if:name = current()]/if:type,"
           + "'bbf-xponift:ani')" {
          error-message
            "The referenced interface is not of type or derived from "
          + "type 'bbf-xponift:ani'.";
          description
            "The referenced interface must be of or derived from type
             'bbf-xponift:ani'.";
        }
        mandatory true;
        description
          "References the Optical Network Unit (ONU) to which the
           virtual User Network Interface (UNI) relates.";
      }
    }
  }
}
