module bbf-sub-interfaces {
  yang-version 1.1;
  namespace "urn:bbf:yang:bbf-sub-interfaces";
  prefix bbf-subif;

  import bbf-frame-processing {
    prefix bbf-fp;
  }
  import ietf-interfaces {
    prefix if;
  }
  import bbf-if-type {
    prefix bbfift;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on the management of
     sub-interfaces as applicable to access network equipment. As
     such, this module is specific to access network equipment (e.g.,
     BBF-specified Access Nodes and FTTdp DPUs).

     Specifically, this module augments an interface with
     sub-interface-specific frame processing configuration.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }
  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2018-12-03 {
    description
      "Amendment 2.
       * Approval Date:    2018-12-03.
       * Publication Date: 2018-12-03.";
    reference
      "TR-383a2: Common YANG Modules
               <https://www.broadband-forum.org/technical/download/
                        TR-383_Amendment-2.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  feature tag-rewrites {
    description
      "This feature indicates whether the network element supports the
       flexible rewrite functionality specifying flexible tag
       rewrites.";
  }

  augment "/if:interfaces/if:interface" {
    when "derived-from-or-self(if:type, 'bbfift:sub-interface')" {
      description
        "Common data that defines the relationship between the
         sub-interface and its lower-layer interface.";
    }
    description
      "Add a reference pointing to a lower-layer interface to those
       interfaces that are of the type sub-interface.";
    container subif-lower-layer {
      description
        "Links the sub-interface to a lower-layer interface.";
      leaf interface {
        type if:interface-ref;
        description
          "References the lower-layer interface.";
      }
    }
    choice frame-processing {
      description
        "Configuration of frame processing.

         Multiple alternatives can be defined. They all have in common
         that the definition of the frame processing is relative to
         the lower-layer interface configured in leaf
         'subif-lower-layer'.

         For example, if there is configuration for ingress frame
         processing, then this means that frames received on the
         referenced lower-layer interface are subject to evaluation
         using the match criteria configured for this sub-interface.
         Not configuring any frame processing case implies that there
         are no ingress match criteria to select frames received from
         the lower-layer interface into this sub-interface, and hence
         this sub-interface will not have to process any ingress
         frame.";
      case inline-frame-processing {
        container inline-frame-processing {
          description
            "The frame processing refers to both directions:
             - Ingress, which refers to frames received from the
               lower-layer interface.
             - Egress, which refers to frames received from a
               higher-layer of the interface stack, or from a
               forwarder, and to be transmitted to the lower-layer of
               the interface stack.
             - In the ingress direction classification criteria
               identify whether a received frame shall be offered to
               this sub-interface.
             - For both the ingress and egress direction, rewrite =
               tag manipulations can be supported.";
          uses bbf-fp:frame-processing {
            refine "ingress-rule/rule/ingress-rewrite" {
              if-feature "tag-rewrites";
            }
            refine "egress-rewrite" {
              if-feature "tag-rewrites";
            }
            augment "ingress-rule/rule" {
              description
                "Defines match criteria for all the fields of VLAN
                 tags, being the TPID, the VLAN ID, the p-bits, and
                 the DEI bit.";
              container flexible-match {
                description
                  "This container provides a generic framework to
                   specify match criteria for frame fields. Specific
                   match criteria shall be provided using augments in
                   a context dependent way, e.g., match criteria can
                   be augmented for VLAN tagged frames, or in another
                   context match criteria can be augmented for MPLS
                   frames.";
              }
            }
          }
        }
      }
    }
  }
}
