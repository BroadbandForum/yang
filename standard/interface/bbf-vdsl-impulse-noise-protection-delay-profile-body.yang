submodule bbf-vdsl-impulse-noise-protection-delay-profile-body {
  yang-version 1.1;
  belongs-to bbf-vdsl {
    prefix bbf-vdsl;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing Broadband Forum TR-252i3 clause 5.7 DSL Quality
     Management related profiles; INP-Delay Profile.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping impulse-noise-protection-delay-profile {
    description
      "The Impulse Noise Protection (INP) Delay profile contains
       INP-Delay parameters for each pair of upstream and downstream
       channels.";
    leaf force-framer-setting-inp {
      type boolean;
      default "false";
      description
        "If retransmission is not used in a given transmit direction,
         this parameter indicates that the framer settings of the
         bearer will be selected such that the Impulse Noise
         Protection (INP) computed according to the formula specified
         in the relevant Recommendation is greater than or equal to
         the minimal impulse noise protection requirement.
         This flag will have the same value for all the bearers
         of one line in the same direction.";
      reference
        "ITU-T G.997.1 clause 7.3.2.5 (FORCEINP)";
    }
    leaf minimum-inp {
      type uint8 {
        range "0..2 | 4 | 6 | 8 | 10 | 12 | 14 | 16 | 18
               | 20 | 22 | 24 | 26 | 28 | 30 | 32" {
          description
            "Defines a range of 0, 0.5 and 1 to 16 symbols.";
        }
      }
      units "0.5 symbols";
      default "0";
      description
        "If retransmission is not used in a given transmit direction,
         this parameter specifies the minimum Impulse Noise Protection
         (INPMIN) for the bearer channel if it is transported over DMT
         symbols with a subcarrier spacing of 4.3125 kHz. The impulse
         noise protection is expressed in Discrete Multi-Tone (DMT)
         symbols with a subcarrier spacing of 4.3125 kHz and can take
         the values and any integer from 0 to 16, inclusive.
         If the xDSL Transceiver Unit (xTU) does not support the
         configured INPMIN value, it will use the nearest supported
         impulse noise protection greater than INPMIN.";
      reference
        "ITU-T G.997.1 clause 7.3.2.3 (INPMIN)";
    }
    leaf minimum-inp-8 {
      type uint8 {
        range "0..16";
      }
      units "symbols";
      default "0";
      description
        "If retransmission is not used in a given transmit direction,
         this parameter specifies the minimum Impulse Noise Protection
         (INP) for the bearer channel if it is transported over
         Discrete Multi-Tone (DMT) symbols with a subcarrier spacing
         of 8.625 kHz. The impulse noise protection is expressed in
         DMT symbols with a subcarrier spacing of 8.625 kHz and can
         take any integer value from 0 to 16, inclusive.";
      reference
        "ITU-T G.997.1 clause 7.3.2.4 (INPMIN8)";
    }
    leaf maximum-interleaving-delay {
      type union {
        type uint8 {
          range "2..63";
        }
        type enumeration {
          enum S0 {
            description
              "The value S0 indicates no delay bound is being
               imposed.";
          }
          enum S1 {
            description
              "The value S1 indicates the fast latency path will be
               used in the G.992.1 operating mode and S and D will
               be selected such that S <= 1 and D = 1 in
               [ITU-T G.992.2], [ITU-T G.992.3], [ITU-T G.992.4],
               [ITU-T G.992.5] and [ITU-T G.993.2]
               operating modes.";
          }
          enum S2 {
            description
              "The value S2 indicates a delay bound of 1 millisecond
               in [ITU-T G.993.2].";
          }
        }
      }
      units "milliseconds";
      default "16";
      description
        "If retransmission is not used in a given transmit direction,
         this parameter is the maximum one-way interleaving delay
         introduced by the Physical Media Specific Transmission
         Convergence (PMS-TC) between the alpha and the beta reference
         points, in the direction of the bearer channel. The one-way
         interleaving delay is defined in individual ADSL
         Recommendations as Roundup(S*D) /4 milliseconds, where S is
         the S-factor and D is the Interleaving Depth and Roundup(x)
         denotes rounding to the higher integer. The xDSL Transceiver
         Units (xTU) will choose the S and D values such that the
         actual one-way interleaving delay is less than or equal to
         the configured maximum interleaving delay.";
      reference
        "ITU-T G.997.1 clauses 7.3.2.2 and 7.5.2.3";
    }
    leaf maximum-delay-rtx {
      type uint8 {
        range "1..63";
      }
      units "milliseconds";
      default "16";
      description
        "If retransmission is used in a given transmit direction,
         this parameter specifies the maximum for the instantaneous
         delay due to the effect of retransmission only. The delay
         ranges from 1 to 63 milliseconds by steps of 1 milisecond.";
      reference
        "ITU-T G.997.1 clause 7.3.2.11 (DELAYMAX_RTX);
         ITU-T G.998.4";
    }
    leaf minimum-delay-rtx {
      type uint8 {
        range "0..62";
      }
      units "milliseconds";
      must '. < ../maximum-delay-rtx' {
        error-message
          "'minimum-delay-rtx' is greater than or equal to "
        + "'maximum-delay-rtx'.";
        description
          "The minimum delay must be less than the maximum delay for
           retransmission.";
      }
      default "0";
      description
        "If retransmission is used in a given transmit direction,
         this parameter specifies the minimum for the instantaneous
         delay due to the effect of retransmission only. The delay
         ranges from 0 to 62 milliseconds by steps of 1 millisecond.";
      reference
        "ITU-T G.997.1 clause 7.3.2.12 (DELAYMIN_RTX);
         ITU-T G.998.4";
    }
    leaf minimum-inp-against-shine-rtx {
      type uint8 {
        range "0..63";
      }
      units "symbols";
      default "0";
      description
        "If retransmission is used in a given transmit direction,
         this parameter specifies the minimum Impulse Noise
         Protection (INP) against Single High Impulse Noise Event
         (SHINE) for the bearer channel if it is transported over
         Discrete Multi-Tone (DMT) symbols with a subcarrier spacing
         of 4.3125 kHz. The impulse noise protection is expressed in
         DMT symbols with a subcarrier spacing of 4.3125 kHz and can
         take any integer value from 0 to 63, inclusive.";
      reference
        "ITU-T G.997.1 clause 7.3.2.13 (INPMIN_SHINE_RTX)";
    }
    leaf minimum-inp-against-shine-8-rtx {
      type uint8 {
        range "0..127";
      }
      units "symbols";
      default "0";
      description
        "If retransmission is used in a given transmit direction,
         this parameter specifies the minimum impulse noise
         protection against Single High Impulse Noise Event (SHINE)
         for the bearer channel if it is transported over Discrete
         Multi-Tone (DMT) symbols with a subcarrier spacing of
         8.625 kHz. The impulse noise protection is expressed
         in DMT symbols with a subcarrier spacing of 8.625 kHz
         and can take any integer value from 0 to 127,
         inclusive.";
      reference
        "ITU-T G.997.1 clause 7.3.2.14 (INPMIN8_SHINE_RTX)";
    }
    leaf shine-ratio-rtx {
      type uint8 {
        range "0..100" {
          description
            "Defines a range from 0.000 to 0.100.";
        }
      }
      units "0.001";
      default "0";
      description
        "If retransmission is used in a given transmit direction,
         this parameter specifies the Single High Impulse Noise Event
         (SHINE) ratio. The values range from 0 to 0.100 in increments
         of 0.001.";
      reference
        "ITU-T G.997.1 clause 7.3.2.15 (SHINERATIO_RTX);
         ITU-T G.998.4";
    }
    leaf minimum-inp-against-rein-rtx {
      type uint8 {
        range "0..7";
      }
      units "symbols";
      default "0";
      description
        "If retransmission is used in a given transmit direction,
         this parameter specifies the minimum impulse noise
         protection against Repetitive Electrical Impulse Noise (REIN)
         for the bearer channel if it is transported over Discrete
         Multi-Tone (DMT) symbols with a subcarrier spacing of 4.3125
         kHz. The impulse noise protection is expressed in DMT symbols
         with a subcarrier spacing of 4.3125 kHz and can take any
         integer value from 0 to 7, inclusive.";
      reference
        "ITU-T G.997.1 clause 7.3.2.16 (INPMIN_REIN_RTX)";
    }
    leaf minimum-inp-against-rein-8-rtx {
      type uint8 {
        range "0..13";
      }
      units "symbols";
      default "0";
      description
        "If retransmission is used in a given transmit direction,
         this parameter specifies the minimum impulse noise
         protection against Repetitive Electrical Impulse Noise (REIN)
         for the bearer channel if it is transported over Discrete
         Multi-Tone (DMT) symbols with a subcarrier spacing of 8.625
         kHz. The impulse noise protection is expressed in DMT symbols
         with a subcarrier spacing of 8.625 kHz and can take any
         integer value from 0 to 13, inclusive.";
      reference
        "ITU-T G.997.1 clause 7.3.2.17 (INPMIN8_REIN_RTX)";
    }
    leaf rein-inter-arrival-time-rtx {
      type enumeration {
        enum 0 {
          description
            "The value 0 indicates an inter-arrival time derived from
             Repetitive Electrical Impulse Noise (REIN) at 100 Hz.";
        }
        enum 1 {
          description
            "The value 1 indicates an inter-arrival time derived from
             Repetitive Electrical Impulse Noise (REIN) at 120 Hz.";
        }
      }
      default "0";
      description
        "If retransmission is used in a given transmit direction, this
         parameter specifies the inter-arrival time that is assumed
         for Repetitive Electrical Impulse Noise (REIN) protection.
         The value 0 indicates an inter-arrival time derived from a
         REIN at 100 Hz. The value 1 indicates an inter-arrival time
         derived from a REIN at 120 Hz. The default is enum 0,
         corresponding to 100 Hz.";
      reference
        "ITU-T G.997.1 clause 7.3.2.18 (IAT_REIN_RTX)";
    }
    leaf maximum-delay-variation {
      type union {
        type uint8 {
          range "1..254" {
            description
              "Defines a range from 0.1 to 25.4 milliseconds.";
          }
        }
        type enumeration {
          enum unbounded {
            description
              "Indicates that no delay variation bound is imposed.";
          }
        }
      }
      units "0.1 milliseconds";
      default "unbounded";
      description
        "This parameter specifies the maximum value for the delay
         variation allowed in an On-Line Reconfiguration (OLR)
         procedure. It ranges from 0.1 to 25.4 in steps of 0.1
         milliseconds. A special value (enum unbounded) indicates that
         no delay variation bound is imposed.";
      reference
        "ITU-T G.997.1 clause 7.3.2.9 (DVMAX)";
    }
    leaf channel-initialization-policy {
      type enumeration {
        enum 0 {
          description
            "CIpolicy=0.";
        }
        enum 1 {
          description
            "CIpolicy=1.";
        }
        enum 2 {
          description
            "CIpolicy=2.";
        }
      }
      default "0";
      description
        "If retransmission is not used in a given transmit direction,
         this parameter indicates which policy will be applied to
         determine the transceiver configuration parameters at
         initialization. The valid values for Channel Initialization
         Policy (CIPOLICY) are 0, 1 and 2. They are defined in the
         respective Recommendations. The default is enum 0,
         corresponding to CIpolicy=0.";
      reference
        "ITU-T G.997.1 clause 7.3.2.10 (CIPOLICY); ITU-T G.993.2
         clause 12.3.7";
    }
  }

  grouping impulse-noise-protection-delay-profile-downstream {
    description
      "The Impulse Noise Protection (INP) Delay profile contains
       INP-Delay parameters for each downstream channel.";
    leaf mdosplit {
      type union {
        type uint8 {
          range "0 | 5..95 | 100";
        }
        type enumeration {
          enum vendor-discretionary {
            description
              "Indicates that that the VDSL Transceiver Unit - central
               Office (VTU-O) is allowed to use a vendor discretionary
               algorithm.";
          }
        }
      }
      units "percent";
      default "vendor-discretionary";
      description
        "The line configuration parameter MAXDELAYOCTET-split
         (MDOSPLIT) defines the percentage of the MAXDELAYOCTET_ext if
         operating in G.998.4 or MAXDELAYOCTET in other cases
         allocated to the downstream direction. All of the remaining
         MAXDELAYOCTET or MAXDELAYOCTET_ext will be allocated for use
         in the upstream direction. The detailed specification is in
         ITU-T G.993.2 and G.998.4. MDOSPLIT will be expressed as a
         percentage, with valid range from 5 percent to 95 percent
         inclusive, in steps of 1 percent. The value 0% is valid only
         if the maximum downstream interleaving delay is configured
         with the special value S1 and retransmission is disabled in
         the downstream direction. The value 100% is valid only if the
         maximum upstream interleaving delay is configured with the
         special value S1 and retransmission is disabled in the
         upstream direction. A special value (enum
         vendor-discretionary) indicates that the VDSL Transceiver
         Unit - central Office (VTU-O) is allowed to use a vendor
         discretionary algorithm.";
      reference
        "ITU-T G.997.1 clauses 7.3.2.2 and 7.3.1.14 (MDOSPLIT);
         ITU-T G.993.2;
         ITU-T G.998.4";
    }
    leaf attndr-method {
      type enumeration {
        enum 0 {
          description
            "Basic method.";
        }
        enum 1 {
          description
            "Improved method using INP_min0.";
        }
        enum 2 {
          description
            "Improved method assuming INP_min0=0.";
        }
      }
      default "0";
      description
        "This downstream parameter specifies the method to be used for
         the calculation of the Attainable Net Data Rate (ATTNDR) in
         the downstream and upstream direction. The parameter can take
         three values 0, 1 and 2. The default is enum 0, corresponding
         to the basic method.";
      reference
        "ITU-T G.997.1 clause 7.3.1.15.1 (ATTNDR_METHOD);
         ITU-T G.993.2 clause 11.4.1.1.7";
    }
    leaf attndr-mdosplit {
      type union {
        type uint8 {
          range "0 | 5..95 | 100";
        }
        type enumeration {
          enum vendor-discretionary {
            description
              "Indicates that the VDSL Transceiver Unit - central
               Office (VTU-O) is allowed to use a vendor discretionary
               algorithm.";
          }
        }
      }
      units "percent";
      default "vendor-discretionary";
      description
        "The line configuration parameter Attainable Net Data Rate
         MAXDELAYOCTET Split (ATTNDR_MDOSPLIT) defines the percentage
         of the MAXDELAYOCTET_ext if operating in G.998.4 or
         MAXDELAYOCTET in other cases allocated to the downstream
         direction to be used in the improved method for calculation
         of the Attainable Net Data Rate (ATTNDR). All of the
         remaining MAXDELAYOCTET_ext or MAXDELAYOCTET will be
         allocated for use in the upstream direction. The detailed
         specification is in ITU-T G.993.2 and G.998.4.
         The valid values are identical to the values of the line
         configuration parameter MDOSPLIT. A special value
         (enum vendor-discretionary) indicates that the VDSL
         Transceiver Unit - central Office (VTU-O) is allowed to use a
         vendor discretionary algorithm.";
      reference
        "ITU-T G.997.1 clause 7.3.1.15.2 (ATTNDR_MDOSPLIT);
         ITU-T G.993.2;
         ITU-T G.998.4";
    }
  }

  grouping impulse-noise-protection-delay-profile-upstream {
    description
      "The Impulse Noise Protection (INP) Delay profile contains
       INP-Delay parameters for each upstream channel.";
    leaf mdosplit {
      type union {
        type uint8 {
          range "0 | 5..95 | 100";
        }
        type enumeration {
          enum vendor-discretionary {
            description
              "Indicates that that the VDSL Transceiver Unit - central
               Office (VTU-O) is allowed to use a vendor discretionary
               algorithm.";
          }
        }
      }
      units "percent";
      default "vendor-discretionary";
      status deprecated;
      description
        "The value of downstream and upstream MAXDELAY0CTET split
         (MDOSPLIT) must add to 100%. As such, configuration of the
         downstream MDOSPLIT is sufficient as the upstream will always
         be 100 minus the downstream MDOSPLIT. For this reason, this
         node has been deprecated.

         The line configuration parameter MAXDELAYOCTET-split
         (MDOSPLIT) defines the percentage of the MAXDELAYOCTET_ext
         if operating in G.998.4 or MAXDELAYOCTET in other cases
         allocated to the downstream direction. All of the remaining
         MAXDELAYOCTET or MAXDELAYOCTET_ext will be allocated for use
         in the upstream direction. The detailed specification is in
         ITU-T G.993.2 and G.998.4. MDOSPLIT will be expressed as a
         percentage, with valid range from 5 percent to 95 percent
         inclusive, in steps of 1 percent. The value 0% is valid only
         if the maximum downstream interleaving delay is configured
         with the special value S1 and retransmission is disabled in
         the downstream direction. The value 100% is valid only if the
         maximum upstream interleaving delay is configured with the
         special value S1 and retransmission is disabled in the
         upstream direction. A special value (enum
         vendor-discretionary) indicates that the VDSL Transceiver
         Unit - central Office (VTU-O) is allowed to use a vendor
         discretionary algorithm.";
      reference
        "ITU-T G.997.1 clauses 7.3.2.2 and 7.3.1.14 (MDOSPLIT);
         ITU-T G.993.2;
         ITU-T G.998.4";
    }
    leaf attndr-method {
      type enumeration {
        enum 0 {
          description
            "Basic method.";
        }
        enum 1 {
          description
            "Improved method using INP_min0.";
        }
        enum 2 {
          description
            "Improved method assuming INP_min0=0.";
        }
      }
      default "0";
      status deprecated;
      description
        "Attainable Net Data Rate Method (ATTNDR_METHOD) is only valid
         for the downstream direction and is now deprecated for the
         upstream. Any configured value for upstream ATTNDR_METHOD is
         to be ignored.

         This downstream parameter specifies the method to be used for
         the calculation of the Attainable Net Data Rate (ATTNDR) in
         the downstream and upstream direction. The parameter can take
         three values 0, 1 and 2. The default is enum 0, corresponding
         to the basic method.";
      reference
        "ITU-T G.997.1 clause 7.3.1.15.1 (ATTNDR_METHOD);
         ITU-T G.993.2 clause 11.4.1.1.7";
    }
    leaf attndr-mdosplit {
      type union {
        type uint8 {
          range "0 | 5..95 | 100";
        }
        type enumeration {
          enum vendor-discretionary {
            description
              "Indicates that the VDSL Transceiver Unit - central
               Office (VTU-O) is allowed to use a vendor discretionary
               algorithm.";
          }
        }
      }
      units "percent";
      default "vendor-discretionary";
      status deprecated;
      description
        "Attainable Net Data Rate MAXDELAYOCTET Split
         (ATTNDR_MDOSPLIT) is only valid for the downstream direction
         and is now deprecated for the upstream. Any configured value
         for upstream ATTNDR_MDOSPLIT is to be ignored.

         The line configuration parameter ATTNDR_MDOSPLIT defines
         the percentage of the MAXDELAYOCTET_ext if operating in
         G.998.4 or MAXDELAYOCTET in other cases allocated to the
         downstream direction to be used in the improved method
         for calculation of the ATTNDR. All of the remaining
         MAXDELAYOCTET_ext or MAXDELAYOCTET will be allocated for
         use in the upstream direction. The detailed specification is
         in ITU-T G.993.2 and G.998.4. The valid values are identical
         to the values of the line configuration parameter MDOSPLIT.
         A special value (enum vendor-discretionary) indicates that
         the VDSL Transceiver Unit - central Office (VTU-O) is allowed
         to use a vendor discretionary algorithm.";
      reference
        "ITU-T G.997.1 clause 7.3.1.15.2 (ATTNDR_MDOSPLIT);
         ITU-T G.993.2;
         ITU-T G.998.4";
    }
  }
}
