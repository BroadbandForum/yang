submodule bbf-fast-threshold-crossing-alert-body {
  yang-version 1.1;
  belongs-to bbf-fast {
    prefix bbf-fast;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of identities associated
     with the management of FAST threshold crossing alerts.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }

  identity fast-threshold-crossing-alert {
    description
      "Base identity for FAST threshold crossing alerts (TCA).

       This identity is abstract and is not be used for a
       threshold crossing alert.";
  }

  identity fast-15min-threshold-crossing-alert {
    base fast-threshold-crossing-alert;
    description
      "A threshold crossing alert associated with performance
       counters collected over the current 15 minute interval
       for FAST Transceiver Unit - central Office (FTU-O) or FAST
       Transceiver Unit - Remote side (FTU-R) channels and lines.

       This identity is abstract and is not be used for a
       threshold crossing alert.";
  }

  identity fast-24hr-threshold-crossing-alert {
    base fast-threshold-crossing-alert;
    description
      "A threshold crossing alert associated with performance
       counters collected over the current 24 hour interval
       for FAST Transceiver Unit - central Office (FTU-O) or FAST
       Transceiver Unit - Remote side (FTU-R) channels and lines.

       This identity is abstract and is not be used for a
       threshold crossing alert.";
  }

  identity ftu-o-15min-channel-code-violations-tca {
    base fast-15min-threshold-crossing-alert;
    description
      "The number of channel code violations during the
       current 15 minute interval has exceeded the configured FAST
       Transceiver Unit - central Office (FTU-O) threshold. This
       threshold crossing alert is optional.";
  }

  identity ftu-o-15min-channel-uncorrectable-dtus-tca {
    base fast-15min-threshold-crossing-alert;
    description
      "The number of received uncorrectable Data Transfer Units (DTU)
       during the current 15 minute interval has exceeded the
       configured FAST Transceiver Unit - central Office (FTU-O)
       threshold. This threshold crossing alert is optional.";
  }

  identity ftu-o-15min-channel-retransmitted-dtus-tca {
    base fast-15min-threshold-crossing-alert;
    description
      "The number of retransmitted Data Transfer Units (DTU) during
       the current 15 minute interval has exceeded the configured
       FAST Transceiver Unit - central Office (FTU-O) threshold. This
       threshold crossing alert is optional.";
  }

  identity ftu-o-15min-line-errored-seconds-tca {
    base fast-15min-threshold-crossing-alert;
    description
      "The number of line Errored Seconds (ES) during the current 15
       minute interval has exceeded the configured FAST Transceiver
       Unit - central Office (FTU-O) threshold.";
  }

  identity ftu-o-15min-line-severely-errored-seconds-tca {
    base fast-15min-threshold-crossing-alert;
    description
      "The number of line Severely Errored Seconds (SES) during the
       current 15 minute interval has exceeded the configured FAST
       Transceiver Unit - central Office (FTU-O) threshold.";
  }

  identity ftu-o-15min-line-loss-of-signal-seconds-tca {
    base fast-15min-threshold-crossing-alert;
    description
      "The number of line Loss of Signal Seconds (LOSS) during the
       current 15 minute interval has exceeded the configured FAST
       Transceiver Unit - central Office (FTU-O) threshold. This
       threshold crossing alert is optional.";
  }

  identity ftu-o-15min-line-loss-of-rmc-seconds-tca {
    base fast-15min-threshold-crossing-alert;
    description
      "The number of line Loss of Robust Management Channel (RMC)
       Seconds (LORS) during the current 15 minute interval has
       exceeded the configured FAST Transceiver Unit - central Office
       (FTU-O) threshold. This threshold crossing alert is optional.";
  }

  identity ftu-o-15min-line-unavailable-seconds-tca {
    base fast-15min-threshold-crossing-alert;
    description
      "The number of received line Unavailable Seconds (UAS) during
       the current 15 minute interval has exceeded the configured FAST
       Transceiver Unit - central Office (FTU-O) threshold.";
  }

  identity ftu-o-15min-line-full-initializations-tca {
    base fast-15min-threshold-crossing-alert;
    description
      "The number of line full initializations during the current
       15 minute interval has exceeded the configured FAST Transceiver
       Unit - central Office (FTU-O) threshold. This threshold
       crossing alert is optional.";
  }

  identity ftu-o-15min-line-failed-initializations-tca {
    base fast-15min-threshold-crossing-alert;
    description
      "The number of line failed initializations during the current
       15 minute interval has exceeded the configured FAST Transceiver
       Unit - central Office (FTU-O) threshold. This threshold
       crossing alert is optional.";
  }

  identity ftu-o-15min-line-fast-initializations-tca {
    base fast-15min-threshold-crossing-alert;
    description
      "The number of line fast initializations during the current 15
       minute interval has exceeded the configured FAST Transceiver
       Unit - central Office (FTU-O) threshold. This threshold
       crossing alert is optional.";
  }

  identity ftu-o-15min-line-failed-fast-initializations-tca {
    base fast-15min-threshold-crossing-alert;
    description
      "The number of line failed fast initializations during the
       current 15 minute interval has exceeded the configured FAST
       Transceiver Unit - central Office (FTU-O) threshold. This
       threshold crossing alert is optional.";
  }

  identity ftu-o-15min-line-spontaneous-interruptions-tca {
    base fast-15min-threshold-crossing-alert;
    description
      "The number of line spontaneous interuptions during the current
       15 minute interval has exceeded the configured FAST Transceiver
       Unit - central Office (FTU-O) threshold. This threshold
       crossing alert is optional.";
  }

  identity ftu-r-15min-channel-code-violations-tca {
    base fast-15min-threshold-crossing-alert;
    description
      "The number of channel code violations during the
       current 15 minute interval has exceeded the configured FAST
       Transceiver Unit - Remote side (FTU-R) threshold. This
       threshold crossing alert is optional.";
  }

  identity ftu-r-15min-channel-uncorrectable-dtus-tca {
    base fast-15min-threshold-crossing-alert;
    description
      "The number of received uncorrectable Data Transfer Units (DTU)
       during the current 15 minute interval has exceeded the
       configured FAST Transceiver Unit - Remote side (FTU-R)
       threshold. This threshold crossing alert is optional.";
  }

  identity ftu-r-15min-channel-retransmitted-dtus-tca {
    base fast-15min-threshold-crossing-alert;
    description
      "The number of retransmitted Data Transfer Units (DTU) during
       the current 15 minute interval has exceeded the configured
       FAST Transceiver Unit - Remote side (FTU-R) threshold. This
       threshold crossing alert is optional.";
  }

  identity ftu-r-15min-line-errored-seconds-tca {
    base fast-15min-threshold-crossing-alert;
    description
      "The number of line Errored Seconds (ES) during the current 15
       minute interval has exceeded the configured FAST Transceiver
       Unit - Remote side (FTU-R) threshold.";
  }

  identity ftu-r-15min-line-severely-errored-seconds-tca {
    base fast-15min-threshold-crossing-alert;
    description
      "The number of line Severely Errored Seconds (SES) during the
       current 15 minute interval has exceeded the configured FAST
       Transceiver Unit - Remote side (FTU-R) threshold.";
  }

  identity ftu-r-15min-line-loss-of-signal-seconds-tca {
    base fast-15min-threshold-crossing-alert;
    description
      "The number of line Loss of Signal Seconds (LOSS) during the
       current 15 minute interval has exceeded the configured FAST
       Transceiver Unit - Remote side (FTU-R) threshold. This
       threshold crossing alert is optional.";
  }

  identity ftu-r-15min-line-loss-of-rmc-seconds-tca {
    base fast-15min-threshold-crossing-alert;
    description
      "The number of line Loss of Robust Management Channel (RMC)
       Seconds (LORS) during the current 15 minute interval has
       exceeded the configured FAST Transceiver Unit - Remote side
       (FTU-R) threshold. This threshold crossing alert is optional.";
  }

  identity ftu-r-15min-line-unavailable-seconds-tca {
    base fast-15min-threshold-crossing-alert;
    description
      "The number of received line Unavailable Seconds (UAS) during
       the current 15 minute interval has exceeded the configured FAST
       Transceiver Unit - Remote side (FTU-R) threshold.";
  }

  identity ftu-o-24hr-channel-code-violations-tca {
    base fast-24hr-threshold-crossing-alert;
    description
      "The number of channel code violations during the current 24
       hour interval has exceeded the configured FAST Transceiver
       Unit - central Office (FTU-O) threshold. This threshold
       crossing alert is optional.";
  }

  identity ftu-o-24hr-channel-uncorrectable-dtus-tca {
    base fast-24hr-threshold-crossing-alert;
    description
      "The number of received uncorrectable Data Transfer Units (DTU)
       during the current 24 hour interval has exceeded the configured
       FAST Transceiver Unit - central Office (FTU-O) threshold. This
       threshold crossing alert is optional.";
  }

  identity ftu-o-24hr-channel-retransmitted-dtus-tca {
    base fast-24hr-threshold-crossing-alert;
    description
      "The number of retransmitted Data Transfer Units (DTU) during
       the current 24 hour interval has exceeded the configured FAST
       Transceiver Unit - central Office (FTU-O) threshold. This
       threshold crossing alert is optional.";
  }

  identity ftu-o-24hr-line-errored-seconds-tca {
    base fast-24hr-threshold-crossing-alert;
    description
      "The number of line Errored Seconds (ES) during the current 24
       hour interval has exceeded the configured FAST Transceiver
       Unit - central Office (FTU-O) threshold.";
  }

  identity ftu-o-24hr-line-severely-errored-seconds-tca {
    base fast-24hr-threshold-crossing-alert;
    description
      "The number of line Severely Errored Seconds (SES) during the
       current 24 hour interval has exceeded the configured FAST
       Transceiver Unit - central Office (FTU-O) threshold.";
  }

  identity ftu-o-24hr-line-loss-of-signal-seconds-tca {
    base fast-24hr-threshold-crossing-alert;
    description
      "The number of line Loss of Signal Seconds (LOSS) during the
       current 24 hour interval has exceeded the configured FAST
       Transceiver Unit - central Office (FTU-O) threshold. This
       threshold crossing alert is optional.";
  }

  identity ftu-o-24hr-line-loss-of-rmc-seconds-tca {
    base fast-24hr-threshold-crossing-alert;
    description
      "The number of line Loss of Robust Management Channel (RMC)
       Seconds (LORS) during the current 24 hour interval has exceeded
       the configured FAST Transceiver Unit - central Office (FTU-O)
       threshold. This threshold crossing alert is optional.";
  }

  identity ftu-o-24hr-line-unavailable-seconds-tca {
    base fast-24hr-threshold-crossing-alert;
    description
      "The number of received line Unavailable Seconds (UAS) during
       the current 24 hour interval has exceeded the configured FAST
       Transceiver Unit - central Office (FTU-O) threshold.";
  }

  identity ftu-o-24hr-line-full-initializations-tca {
    base fast-24hr-threshold-crossing-alert;
    description
      "The number of line full initializations during the current
       24 hour interval has exceeded the configured FAST Transceiver
       Unit - central Office (FTU-O) threshold. This threshold
       crossing alert is optional.";
  }

  identity ftu-o-24hr-line-failed-initializations-tca {
    base fast-24hr-threshold-crossing-alert;
    description
      "The number of line failed initializations during the current
       24 hour interval has exceeded the configured FAST Transceiver
       Unit - central Office (FTU-O) threshold. This threshold
       crossing alert is optional.";
  }

  identity ftu-o-24hr-line-fast-initializations-tca {
    base fast-24hr-threshold-crossing-alert;
    description
      "The number of line fast initializations during the current 24
       hour interval has exceeded the configured FAST Transceiver
       Unit - central Office (FTU-O) threshold. This threshold
       crossing alert is optional.";
  }

  identity ftu-o-24hr-line-failed-fast-initializations-tca {
    base fast-24hr-threshold-crossing-alert;
    description
      "The number of line failed fast initializations during the
       current 24 hour interval has exceeded the configured FAST
       Transceiver Unit - central Office (FTU-O) threshold. This
       threshold crossing alert is optional.";
  }

  identity ftu-o-24hr-line-spontaneous-interruptions-tca {
    base fast-24hr-threshold-crossing-alert;
    description
      "The number of line spontaneous interuptions during the current
       24 hour interval has exceeded the configured FAST Transceiver
       Unit - central Office (FTU-O) threshold. This threshold
       crossing alert is optional.";
  }

  identity ftu-r-24hr-channel-code-violations-tca {
    base fast-24hr-threshold-crossing-alert;
    description
      "The number of channel code violations during the
       current 24 hour interval has exceeded the configured FAST
       Transceiver Unit - Remote side (FTU-R) threshold. This
       threshold crossing alert is optional.";
  }

  identity ftu-r-24hr-channel-uncorrectable-dtus-tca {
    base fast-24hr-threshold-crossing-alert;
    description
      "The number of received uncorrectable Data Transfer Units (DTU)
       during the current 24 hour interval has exceeded the configured
       FAST Transceiver Unit - Remote side (FTU-R) threshold. This
       threshold crossing alert is optional.";
  }

  identity ftu-r-24hr-channel-retransmitted-dtus-tca {
    base fast-24hr-threshold-crossing-alert;
    description
      "The number of retransmitted Data Transfer Units (DTU) during
       the current 24 hour interval has exceeded the configured FAST
       Transceiver Unit - Remote side (FTU-R) threshold. This
       threshold crossing alert is optional.";
  }

  identity ftu-r-24hr-line-errored-seconds-tca {
    base fast-24hr-threshold-crossing-alert;
    description
      "The number of line Errored Seconds (ES) during the current 24
       hour interval has exceeded the configured FAST Transceiver
       Unit - Remote side (FTU-R) threshold.";
  }

  identity ftu-r-24hr-line-severely-errored-seconds-tca {
    base fast-24hr-threshold-crossing-alert;
    description
      "The number of line Severely Errored Seconds (SES) during the
       current 24 hour interval has exceeded the configured FAST
       Transceiver Unit - Remote side (FTU-R) threshold.";
  }

  identity ftu-r-24hr-line-loss-of-signal-seconds-tca {
    base fast-24hr-threshold-crossing-alert;
    description
      "The number of line Loss of Signal Seconds (LOSS) during the
       current 24 hour interval has exceeded the configured FAST
       Transceiver Unit - Remote side (FTU-R) threshold. This
       threshold crossing alert is optional.";
  }

  identity ftu-r-24hr-line-loss-of-rmc-seconds-tca {
    base fast-24hr-threshold-crossing-alert;
    description
      "The number of line loss of Robust Management Channel (RMC)
       seconds during the current 24 hour interval has exceeded the
       configured FAST Transceiver Unit - Remote side (FTU-R)
       threshold. This threshold crossing alert is optional.";
  }

  identity ftu-r-24hr-line-unavailable-seconds-tca {
    base fast-24hr-threshold-crossing-alert;
    description
      "The number of received line Unavailable Seconds (UAS) during
       the current 24 hour interval has exceeded the configured FAST
       Transceiver Unit - Remote side (FTU-R) threshold.";
  }
}
