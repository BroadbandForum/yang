submodule bbf-vdsl-sos-profile-body {
  yang-version 1.1;
  belongs-to bbf-vdsl {
    prefix bbf-vdsl;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing Broadband Forum TR-252i3 clause 5.7 DSL Quality
     Management related profiles; Save Our Showtime (SOS) Profile.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping sos-profile {
    description
      "The Save Our Showtime (SOS) Profile provides the parameters to
       configure the optional procedure for VDSL2 SOS, which rapidly
       falls back to a lower speed without a re-initialization.";
    leaf sos-time {
      type union {
        type uint8 {
          range "1..255";
        }
        type enumeration {
          enum disabled {
            description
              "Indicates that the standard Save Our Showtime (SOS)
               triggering criteria are disabled, i.e., vendor
               discretionary values may be used.";
          }
        }
      }
      units "64 milliseconds";
      default "disabled";
      description
        "The parameter SOS-TIME is used in the specification of the
         receiver initiated Save Our Showtime (SOS). If the value of
         this parameter is not zero, the standard SOS triggering
         criteria are enabled, and the value corresponds with duration
         of the time window used in the standard SOS triggering
         criteria in the direction of transmission. The special value
         (enum disabled) indicates that the standard SOS triggering
         criteria are disabled, i.e., vendor discretionary values may
         be used instead of the values configured in the Management
         Information Base (MIB) for the following parameters:
         SOS-NTONES, SOS-CRC, SOS-TIME. The valid range of values is
         from 64 milliseconds to 16320 milliseconds in steps of 64
         milliseconds.

         If any of the nodes 'sos-time', 'sos-ntones', or 'sos-crc'
         are configured to be 'disabled', then the behavior is the
         same as 'sos-time' being disabled.";
      reference
        "ITU-T G.997.1 clauses 7.3.1.10.1 (SOS-TIME-ds) and
         7.3.1.10.2 (SOS-TIME-us);
         ITU-T G.993.2 clause 13.4.3";
    }
    leaf sos-ntones {
      type union {
        type uint8 {
          range "1..100";
        }
        type enumeration {
          enum disabled {
            description
              "Indicates that the standard Save Our Showtime (SOS)
               triggering criteria are disabled, i.e., vendor
               discretionary values may be used.";
          }
        }
      }
      units "percent";
      default "disabled";
      description
        "This parameter is defined as the minimum percentage of
         tones in the MEDLEY SET in the direction of transmission
         that will be degraded in order to arm the first sub-condition
         of the standard Save Our Showtime (SOS) triggering criteria.
         The parameter SOS-NTONES is defined as a percentage of tones.
         The valid range of values is from 1 to 100 in steps of 1. The
         special value (enum disabled) indicates that the standard SOS
         triggering criteria are disabled.

         If any of the nodes 'sos-time', 'sos-ntones', or 'sos-crc'
         are configured to be 'disabled', then the behavior is the
         same as 'sos-time' being disabled.";
      reference
        "ITU-T G.997.1 clauses 7.3.1.10.3 (SOS-NTONES-ds) and
         7.3.1.10.4 (SOS-NTONES-us);
         ITU-T G.993.2 clause 13.4.3.2";
    }
    leaf sos-crc {
      type union {
        type uint16 {
          range "1..65535";
        }
        type enumeration {
          enum disabled {
            description
              "Indicates that the standard Save Our Showtime (SOS)
               triggering criteria are disabled, i.e., vendor
               discretionary values may be used.";
          }
        }
      }
      default "disabled";
      description
        "This parameter is defined as the minimum number of
         normalized Cyclic Redundancy Check (CRC) anomalies received
         in SOS-TIME seconds in order to arm the second sub-condition
         of the standard Save Our Showtime (SOS) triggering criteria
         in the direction of transmission. The valid range of SOS-CRC
         values is 0.02 to ((2^16)-1)*0.02, in steps of 0.02.
         Additionally, the special value (enum disabled) indicates
         that the standard SOS triggering criteria are disabled.

         If any of the nodes 'sos-time', 'sos-ntones', or 'sos-crc'
         are configured to be 'disabled', then the behavior is the
         same as 'sos-time' being disabled.";
      reference
        "ITU-T G.997.1 clauses 7.3.1.10.5 (SOS-CRC-ds) and 7.3.1.10.6
         (SOS-CRC-us);
         ITU-T G.993.2 clause 13.4.3.2";
    }
    leaf max-sos {
      type union {
        type uint8 {
          range "1..15";
        }
        type enumeration {
          enum unlimited {
            description
              "Indicates that there is no limit on the maximum
               allowed number of Save Our Showtime (SOS) recoveries
               within this time interval.";
          }
        }
      }
      default "unlimited";
      description
        "This parameter is used in G.993.2 de-activation. If the
         number of successful Save Our Showtime (SOS) procedures in
         the direction of transmission performed within a 120 second
         interval exceeds MAX-SOS, the modem will transition to the L3
         state. The valid range of values is 1 to 15. The special
         value (enum unlimited) indicates that there is no limit on
         the maximum allowed number of SOS recoveries within this time
         interval.";
      reference
        "ITU-T G.997.1 clauses 7.3.1.10.7 (MAX-SOS-ds) and 7.3.1.10.8
         (MAX-SOS-us);
         ITU-T G.993.2 clause 12.1.4";
    }
    leaf snrmoffset-roc {
      type uint16 {
        range "0..310" {
          description
            "Defines a range from 0.0 to 31.0 dB.";
        }
      }
      units "0.1 dB";
      default "0";
      description
        "The parameter is defined as the Signal-To-Noise (SNR) Margin
         offset for the Robust Overhead Channel (ROC) in the direction
         of transmission. The parameter is used in the specification
         of the channel initialization policy. The valid range of SNR
         margin offset values is from 0 to 31 dB, with 0.1 dB steps.";
      reference
        "ITU-T G.997.1 clauses 7.3.1.10.9 (SNRMOFFSET-ROC-ds) and
         7.3.1.10.10 (SNRMOFFSET-ROC-us);
         ITU-T G.993.2 clause 12.3.7.1";
    }
    leaf inpmin-roc {
      type uint8 {
        range "0..8";
      }
      units "T4k periods";
      default "0";
      description
        "This parameter contains the minimum impulse noise protection
         (INPMIN) to apply on the Robust Overhead Channel (ROC) in the
         direction of transmission. The minimum impulse noise
         protection is an integer ranging from 0 to 8 representing the
         number of T4k periods. A T4k period is about 250
         microseconds.";
      reference
        "ITU-T G.997.1 clauses 7.3.1.10.11 (INPMIN-ROC-ds) and
         7.3.1.10.12 (INPMIN-ROC-us)";
    }
  }
}
