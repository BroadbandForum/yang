submodule bbf-fast-fast-retrain-policy-profile-body {
  yang-version 1.1;
  belongs-to bbf-fast {
    prefix bbf-fast;
  }

  include bbf-fast-base;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing fast retrain policy profiles.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping fast-retrain-policy-parameters {
    description
      "Reinitialization configuration parameters applicable to both
       upstream and downstream.";
    reference
      "ITU-T G.997.2 clause 7.1.8";
    leaf los-defect-persistency {
      type uint8 {
        range "1..20" {
          description
            "Defines a range from 0.1 to 2.0 seconds.";
        }
      }
      units "0.1 seconds";
      default "2";
      description
        "Defines the loss of signal (los) defect persistency for
         triggering a reinitialization at the FAST Transceiver Unit
         (FTU) receiver, as part of the fast retrain policy.";
      reference
        "ITU-T G.997.2 clauses 7.1.8.1 (LOS_PERSISTENCYds) and clause
         7.1.8.2 (LOS_PERSISTENCYus);
         ITU-T G.9701 clauses 12.1.4.2 and 12.1.4.3.1";
    }
    leaf lom-defect-persistency {
      type uint8 {
        range "1..20";
      }
      units "seconds";
      default "2";
      description
        "Defines the loss of margin (lom) defect persistency for
         triggering a reinitialization at the FAST Transceiver Unit
         (FTU) receiver, as part of the fast retrain policy.";
      reference
        "ITU-T G.997.2 clauses 7.1.8.3 (LOM_PERSISTENCYds) and clause
         7.1.8.4 (LOM_PERSISTENCYus);
         ITU-T G.9701 clauses 12.1.4.2 and 12.1.4.3.2.";
    }
    leaf lor-defect-persistency {
      type uint8 {
        range "1..20" {
          description
            "Defines a range from 0.1 to 2.0 seconds.";
        }
      }
      units "0.1 seconds";
      default "2";
      description
        "Defines the loss of Robust Management Channel (RMC) (lor)
         defect persistency for triggering a reinitialization at the
         FAST Transceiver Unit (FTU) receiver, as part of the fast
         retrain policy.";
      reference
        "ITU-T G.997.2 clauses 7.1.8.5 (LOR_PERSISTENCYds) and clause
         7.1.8.6 (LOR_PERSISTENCYus);
         ITU-T G.9701 clauses 12.1.4.2 and 12.1.4.3.3.";
    }
    leaf reinit-time-threshold {
      type uint8 {
        range "5..31";
      }
      units "seconds";
      default "10";
      description
        "Defines the threshold for the Severly Errored Seconds (SES)
         and embedded operations channel (eoc) timeout conditions for
         declaring a High_BER event at the FAST Transceiver Unit (FTU)
         receiver, as part of the fast retrain policy.";
      reference
        "ITU-T G.997.2 clauses 7.1.8.7 (REINIT_TIME_THRESHOLDds) and
         clause 7.1.8.8 (REINIT_TIME_THRESHOLDus);
         ITU-T G.9701 clause 12.1.4.3.4.";
    }
    leaf low-etr-threshold {
      type uint8 {
        range "0 | 1..30";
      }
      units "seconds";
      default "20";
      description
        "Defines the threshold for the low Expected Throughput Rate
         (ETR) condition for declaring a High_BER event at the FAST
         Transceiver Unit (FTU) receiver, as part of the fast retrain
         policy. The special value, 0, indicates that no High_BER
         event is declared based on ETR being below the ETR_min.";
      reference
        "ITU-T G.997.2 clause 7.1.8.9 (LOW_ETR_THRESHOLDds) and
         clause 7.1.8.10 (LOW_ETR_THRESHOLDus);
         ITU-T G.9701 clause 12.1.4.3.4.";
    }
    leaf lor-rmcr-persistency {
      if-feature "bbf-fast:rmcr";
      type uint8 {
        range "0..20" {
          description
            "Defines a range from 0 to 1000 milliseconds.";
        }
      }
      units "50 milliseconds";
      default "0";
      description
        "Defines the persistency period of a loss of Robust Management
         Channel (RMC) (lor) defect before the RMC is declared
         severely degraded. The value 0 is a special value that
         indicates that the Robust Management Channel Recovery (RMCR)
         procedure is disabled. It can only be set to 0 in one
         direction if the value is also set to 0 in the opposite
         direction.";
      reference
        "ITU-T G.997.2 clause 7.1.12.1 (RMCR_LOR_TRIGGERds/us)";
    }
  }

  grouping fast-retrain-policy-profile {
    description
      "Defines the contents of a Fast Retrain Policy Profile.";
    container downstream {
      description
        "Downstream fast retrain policy parameters.";
      uses fast-retrain-policy-parameters;
    }
    container upstream {
      description
        "Downstream fast retrain policy parameters.";
      uses fast-retrain-policy-parameters;
    }
  }
}
