module bbf-xpon-burst-profiles {
  yang-version 1.1;
  namespace "urn:bbf:yang:bbf-xpon-burst-profiles";
  prefix bbf-xpon-burst-prof;

  import ietf-interfaces {
    prefix if;
  }
  import bbf-xpon {
    prefix bbf-xpon;
  }
  import bbf-xponvani {
    prefix bbf-xponvani;
  }

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).

     Specifically, this module provides management of burst profiles.

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }
  revision 2024-04-23 {
    description
      "Issue 3.
       * Approval Date:    2024-04-23.
       * Publication Date: 2024-04-23.";
    reference
      "TR-385i3: YANG Modules for PON Management
               <https://www.broadband-forum.org/technical/download/
                        TR-385_Issue-3.pdf>";
  }
  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }

  feature configurable-burst-profile {
    description
      "Indicates support for the upstream burst profile
       configuration.";
  }

  grouping burst-profile-configuration-data {
    description
      "Configuration data data for an upstream burst profiles.";
    list burst-profile {
      key "profile-id";
      description
        "The list of burst profiles.";
      leaf profile-id {
        type uint8 {
          range "0..3";
        }
        description
          "Burst profile ID.";
        reference
          "ITU-T G.987.3 Clause 8.1.2.6;
           ITU-T G.987.3 Clasue 11.3.3;
           ITU-T G.9807.1 Clause C.8.1.1.2.6;
           ITU-T G.9807.1 Clause C.11.3.3.1;
           ITU-T G.989.3 Clause 8.1.1.2.6;
           ITU-T G.989.3 Clause 11.3.3.1;
           ITU-T G.9804.2 Clause 8.1.2.6;
           ITU-T G.9804.2 Clause 11.3.3.1";
      }
      leaf profile-version {
        type uint8 {
          range "0..15";
        }
        default "0";
        description
          "Burst profile version. For 50G-PON, the applicable values
           are in [0..7].";
        reference
          "ITU-T G.987.3 Clause 11.3.3;
           ITU-T G.9807.1 Clause C.11.3.3.1;
           ITU-T G.9809.3 Clause 11.3.3.1;
           ITU-T G.9804.2 Clause 11.3.3.1";
      }
      leaf delimiter {
        type string {
          pattern '([a-fA-F0-9][a-fA-F0-9]){0,8}';
        }
        description
          "Delimiter pattern. A string representing 0-8 octets whereas
           each octet is represented as 2 hexadecimal ASCII
           characters.";
        reference
          "ITU-T G.987.3 Clause 11.3.3;
           ITU-T G.9807.1 Clause C.11.3.3.1;
           ITU-T G.9809.3 Clause 11.3.3.1;
           ITU-T G.9804.2 Clause 11.3.3.1";
      }
      leaf preamble {
        type string {
          pattern '([a-fA-F0-9][a-fA-F0-9]){0,8}';
        }
        description
          "Preamble pattern. A string representing 0-8 octets whereas
           each octet is represented as 2 hexadecimal ASCII
           characters.";
        reference
          "ITU-T G.987.3 Clause 11.3.3;
           ITU-T G.9807.1 Clause C.11.3.3.1;
           ITU-T G.9809.3 Clause 11.3.3.1;
           ITU-T G.9804.2 Clause 11.3.3.1";
      }
      leaf preamble-repeat-count {
        type uint8;
        default "1";
        description
          "Number of times the preamble is transmitted. The value 0
           specifies that no preamble is transmitted.

           This leaf is used only for XGS-PON (ITU-T G.9807.1) and
           NG-PON2 (ITU-T G.989.3) channel terminations.";
        reference
          "ITU-T G.9807.1 Clause C.11.3.3.1;
           ITU-T G.9809.3 Clause 11.3.3.1";
      }
      leaf preamble-word-count {
        type uint16;
        description
          "Preamble word count, in 64 bit words, range 0..Wmax, where
           Wmax denotes the maximum word count, and should depend on
           the upstream line rate. The value 0 specifies that no
           preamble is transmitted.

           This leaf is used only for 50G-PON (ITU-T G.9804.2).";
        reference
          "ITU-T G.9804.2 Clause 11.3.3.1";
      }
    }
  }

  augment "/if:interfaces/if:interface/bbf-xpon:channel-termination" {
    description
      "Augment an xPON channel termination configuration with
       data nodes related to upstream burst profile.";
    container burst-profiles {
      if-feature "bbf-xpon-burst-prof:configurable-burst-profile";
      uses bbf-xpon-burst-prof:burst-profile-configuration-data;
      description
        "Upstream burst profile configuration. Burst profiles in the
         burst-profile list are broadcast to all ONUs connected to
         the channel-termination.";
      leaf ranging-burst-profile-id {
        if-feature "bbf-xpon-burst-prof:configurable-burst-profile";
        type uint8 {
          range "0..3";
        }
        description
          "Burst profile ID for ranging time allocations.";
        reference
          "ITU-T G.987.3 Clause 8.1.2.6;
           ITU-T G.9807.1 Clause C.8.1.1.2.6;
           ITU-T G.989.3 Clause 8.1.1.2.6";
      }
    }
  }

  augment "/if:interfaces/if:interface/bbf-xponvani:v-ani" {
    description
      "Augment an xPON virtual Access Network Interface (vANI), i.e.,
       an Optical Network Unit (ONU) as seen by the Optical Line
       Termination (OLT), with data nodes related to upstream burst
       profile.";
    container burst-profiles {
      if-feature "bbf-xpon-burst-prof:configurable-burst-profile";
      uses bbf-xpon-burst-prof:burst-profile-configuration-data;
      description
        "Upstream burst profile configuration. Burst profiles in
         the burst-profile list are transmitted only to the ONU
         associated with the v-ani.";
      leaf data-burst-profile-id {
        if-feature "bbf-xpon-burst-prof:configurable-burst-profile";
        type uint8 {
          range "0..3";
        }
        description
          "Burst profile ID for data allocations.";
        reference
          "ITU-T G.987.3 Clause 8.1.2.6;
           ITU-T G.9807.1 Clause C.8.1.1.2.6;
           ITU-T G.989.3 Clause 8.1.1.2.6";
      }
    }
  }
}
