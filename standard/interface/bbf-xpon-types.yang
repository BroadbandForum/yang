module bbf-xpon-types {
  yang-version 1.1;
  namespace "urn:bbf:yang:bbf-xpon-types";
  prefix bbf-xpon-types;

  import ietf-inet-types {
    prefix inet;
  }

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on the management of
     Passive Optical Network (PON) interfaces. As such, this module
     is specific to access network equipment (e.g., BBF-specified
     Access Nodes and FTTdp DPUs).

     Specifically, this module defines common YANG types used in the
     management of xPON.

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }
  revision 2024-04-23 {
    description
      "Issue 3.
       * Approval Date:    2024-04-23.
       * Publication Date: 2024-04-23.";
    reference
      "TR-385i3: YANG Modules for PON Management
               <https://www.broadband-forum.org/technical/download/
                        TR-385_Issue-3.pdf>";
  }
  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }
  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }
  revision 2019-02-25 {
    description
      "Initial revision.
       * Approval Date:    2019-02-25.
       * Publication Date: 2019-02-25.";
    reference
      "TR-385: ITU-T PON YANG Modules
               <https://www.broadband-forum.org/technical/download/
                        TR-385.pdf>";
  }

  feature support-unconditional-onu-authentication-by-mgmt-plane {
    description
      "Indicates support for configuring the value
       'by-management-plane' as 'auth-method-type'.";
  }

  feature support-unconditional-onu-authentication-by-d-olt {
    description
      "Indicates support for configuring the value 'by-d-olt' as
       'auth-method-type'.";
  }

  identity type-b-state-base {
    description
      "This identity is used as the base for possible
       channel-terminations states for type B protection.";
  }

  identity active {
    base type-b-state-base;
    description
      "This identity is used to denote active state in type B
       protection.";
  }

  identity standby {
    base type-b-state-base;
    description
      "This identity is used to denote standby state in type B
       protection.";
  }

  identity not-part-of-type-b {
    base type-b-state-base;
    description
      "This identity is used to denote that the object is not part
       of a type B protection scheme. This is for instance the case
       when a channel-termination does not (yet) refer to a
       channel-pair.";
  }

  identity location-base {
    description
      "This identity is used as the possible locations of an object.";
  }

  identity inside-olt {
    base location-base;
    description
      "This identity is used to denote a location physically inside
       the Optical Line Termination (OLT) chassis.";
  }

  identity outside-olt {
    base location-base;
    description
      "This identity is used to denote a location physically outside
       the Optical Line Termination (OLT) chassis.";
  }

  identity xpon-type-base {
    description
      "Base identity from which specific xPON types are derived.";
  }

  identity channel-pair-type-base {
    description
      "This identity is used to qualify the possible types of a
       channel-pair.";
  }

  identity fiftyg-twdm {
    base channel-pair-type-base;
    base xpon-type-base;
    description
      "This identity is used to denote a Time Wavelength Division
       Multiplexing (TWDM) 50G-PON channel pair, per ITU-T G.9804.2.";
    reference
      "ITU-T G.9804.2";
  }

  identity fiftyg-tdm {
    base channel-pair-type-base;
    base xpon-type-base;
    description
      "This identity is used to denote a Time Division Multiplexing
       (TDM) 50G-PON channel pair, per ITU-T G.9804.2.";
    reference
      "ITU-T G.9804.2";
  }

  identity twentyfivegs {
    base channel-pair-type-base;
    base xpon-type-base;
    description
      "This identity is used to denote a Time Division Multiplexing
       (TDM) 25GS-PON channel pair, per MSA 25GS-PON Specification.";
    reference
      "MSA 25GS-PON";
  }

  identity ngpon2-twdm {
    base channel-pair-type-base;
    base xpon-type-base;
    description
      "This identity is used to denote a Time Wavelength Division
       Multiplexing (TWDM) NG-PON2 channel pair, per ITU-T G.989.3.";
    reference
      "ITU-T G.989.3";
  }

  identity ngpon2-ptp {
    base channel-pair-type-base;
    base xpon-type-base;
    description
      "This identity is used to denote a Point-to-Point (PtP) NG-PON2
       channel pair, per ITU-T G.989.3.";
    reference
      "ITU-T G.989.3";
  }

  identity xgs {
    base channel-pair-type-base;
    base xpon-type-base;
    description
      "This identity is used to denote an XGS-PON channel pair, per
       ITU-T G.9807.1.";
    reference
      "ITU-T G.9807.1";
  }

  identity xgpon {
    base channel-pair-type-base;
    base xpon-type-base;
    description
      "This identity is used to denote an XG-PON channel pair, per
       ITU-T G.987.3.";
    reference
      "ITU-T G.987.3";
  }

  identity gpon {
    base channel-pair-type-base;
    base xpon-type-base;
    description
      "This identity is used to denote an G-PON channel pair, per
       ITU-T G.984.3.";
    reference
      "ITU-T G.984.3";
  }

  identity channel-pair-line-rate-profile-base {
    description
      "This identity is used to define the possible combinations of
       downstream and upstream line-rates for an NG-PON2
       channel-pair.";
  }

  identity unplanned-cp-line-rate {
    base channel-pair-line-rate-profile-base;
    description
      "This identity is used to denote an NG-PON2 channel pair with
       yet undefined downstream and upstream line rates.";
  }

  identity down-10-up-10 {
    base channel-pair-line-rate-profile-base;
    description
      "This identity is used to denote an NG-PON2 channel pair with
       downstream 10Gbps and upstream 10Gbps line rates.";
  }

  identity down-10-up-2.5 {
    base channel-pair-line-rate-profile-base;
    description
      "This identity is used to denote an NG-PON2 channel pair with
       downstream 10Gbps and upstream 2.5Gbps line rates.";
  }

  identity down-2.5-up-2.5 {
    base channel-pair-line-rate-profile-base;
    description
      "This identity is used to denote an NG-PON2 channel pair with
       downstream 2.5Gbps and upstream 2.5Gbps line rates.";
  }

  identity fiftyg-channel-pair-line-rate-profile-base {
    description
      "This identity is used to define the possible combinations
       of downstream and upstream line-rates for a 50G-PON
       channel-pair.";
    reference
      "ITU-T G.9804.3 Clause 9.2.1;
       ITU-T G.9804.2 Clause 1.1";
  }

  identity unplanned-50g-cp-line-rate {
    base fiftyg-channel-pair-line-rate-profile-base;
    description
      "This identity is used to denote a 50G-PON channel pair with
       yet undefined downstream and upstream line rates.";
  }

  identity down-50-up-50 {
    base fiftyg-channel-pair-line-rate-profile-base;
    description
      "This identity is used to denote a 50G-PON channel pair with
       downstream 50Gbps and upstream 50Gbps line rates.";
    reference
      "ITU-T G.9804.3 Clause 9.2.1;
       ITU-T G.9804.2 Clause 1.1";
  }

  identity down-50-up-25 {
    base fiftyg-channel-pair-line-rate-profile-base;
    description
      "This identity is used to denote a 50G-PON channel pair with
       downstream 50Gbps and upstream 25Gbps line rates.";
    reference
      "ITU-T G.9804.3 Clause 9.2.1;
       ITU-T G.9804.2 Clause 1.1";
  }

  identity down-50-up-12.5 {
    base fiftyg-channel-pair-line-rate-profile-base;
    description
      "This identity is used to denote a 50G-PON channel pair with
       downstream 50Gbps and upstream 12.5Gbps line rates.";
    reference
      "ITU-T G.9804.3 Clause 9.2.1;
       ITU-T G.9804.2 Clause 1.1";
  }

  identity twentyfivegs-channel-pair-line-rate-profile-base {
    description
      "This identity is used to define the possible combinations of
       downstream and upstream line-rates for a 25GS-PON
       channel-pair.";
    reference
      "MSA 25GS-PON Table C.6.1";
  }

  identity unplanned-25gs-cp-line-rate {
    base twentyfivegs-channel-pair-line-rate-profile-base;
    description
      "This identity is used to denote a 25GS-PON channel pair with
       yet undefined downstream and upstream line rates.";
  }

  identity down-25-up-25 {
    base twentyfivegs-channel-pair-line-rate-profile-base;
    description
      "This identity is used to denote a 25GS-PON channel pair with
       downstream 25Gbps and upstream 25Gbps line rates.";
    reference
      "MSA 25GS-PON Table C.6.1";
  }

  identity down-25-up-10 {
    base twentyfivegs-channel-pair-line-rate-profile-base;
    description
      "This identity is used to denote a 25GS-PON channel pair with
       downstream 25Gbps and upstream 10Gbps line rates.";
    reference
      "MSA 25GS-PON Table C.6.1";
  }

  identity tcp-connection-state-base {
    description
      "This identity is used to denote the possible states of a
       Transmission Control Protocol (TCP) connection.";
  }

  identity established {
    base tcp-connection-state-base;
    description
      "This identity is used to reflect that the Transmission Control
       Protocol (TCP) connection is established.";
  }

  identity not-established {
    base tcp-connection-state-base;
    description
      "This identity is used to reflect that the Transmission Control
       Protocol (TCP) connection is not established.";
  }

  identity unknown {
    base tcp-connection-state-base;
    description
      "This identity is used to reflect that the Transmission Control
       Protocol (TCP) connection state is not known.";
  }

  identity action-request-status {
    description
      "This identity is used to denote the status following the
       reception of an action.";
  }

  identity request-being-processed {
    base action-request-status;
    description
      "This identity is used to denote that the Optical Line
       Termination (OLT) has received the action request and is
       handling it.";
  }

  identity request-rejected {
    base action-request-status;
    description
      "This identity is used to denote that the Optical Line
       Termination (OLT) has rejected the action request and will not
       perform anything further.";
  }

  typedef string-hex14 {
    type string {
      pattern '[a-fA-F0-9]{14}';
    }
    description
      "A string representing 7 hexadecimal octets expressed in
       ASCII.";
  }

  typedef pon-id-display-type {
    type union {
      type uint32;
      type string-hex14;
    }
    description
      "A type meant for the different formats of the PON-ID for the
       various channel-pair types. The 'uint32' is meant for 50G-PON,
       NG-PON2, XGS-PON and XG-PON, and the 'string-hex14' is meant
       for G-PON.";
  }

  typedef composite-channel-id-type {
    type union {
      type uint8 {
        range "0..7";
      }
      type enumeration {
        enum xgs {
          description
            "To be used in case of XGS-PON, rather than 0.";
        }
        enum twentyfivegs {
          description
            "To be used in case of 25GS-PON, rather than 0.";
        }
      }
    }
    description
      "A composite type strictly meant for leaves reflecting the
       already allocated downstream or upstream channel-id on a
       channel-group.

       Such leaves are used to prevent conflicts when allocating
       a channel-pair to a channel-group. For NG-PON2, the applicable
       values are in [0..7], for XGS-PON a dedicated value 'xgs' is
       used rather than '0' to prevent ambiguity between this and the
       valid value '0' for NG-PON2.";
  }

  typedef composite-downstream-wavelength-type {
    type union {
      type uint32;
      type enumeration {
        enum xgs {
          description
            "To be used in case of XGS-PON.";
        }
        enum xgpon {
          description
            "To be used in case of XG-PON.";
        }
        enum gpon {
          description
            "To be used in case of G-PON.";
        }
      }
    }
    description
      "A composite type meant for data nodes reflecting the
       downstream wavelengths that are in use on a channel-group.
       A wavelenth used for 25GS-PON, NG-PON2 or XGS should be
       reported as a numeric value expressed in hundredths of nm to
       fit ITU-T precision requirements.

       A wavelength used for XG-PON or G-PON can be reported as a
       numeric value expressed in hundredths of nm or alternately
       with enum value 'xgpon' or 'gpon', respectively.

       The enum value 'xgs' should be avoided: it makes sense only
       when the OLT supports only one of the XGS 'Basic' or 'Optional'
       wavelength sets; the 'xgs' enum value is ambiguous otherwise.";
    reference
      "ITU-T G.9807.1 Clause A.8.2";
  }

  typedef auth-method-type {
    type enumeration {
      enum serial-number {
        description
          "Authentication based on Optical Network Unit (ONU) serial
           number.";
        reference
          "ITU-T G.984.3 Clause VI.1";
      }
      enum loid {
        description
          "Authentication based on the Logical Optical Network Unit
           (ONU) ID (LOID).";
        reference
          "ITU-T G.988 Clause 9.1.1";
      }
      enum registration-id {
        description
          "Authentication based on Optical Network Unit (ONU)
           registration ID.";
        reference
          "ITU-T G.984.3 Clause VI.2";
      }
      enum omci {
        description
          "Authentication by use of the enhanced security control
           managed entity (ME) over OMCI.";
        reference
          "ITU-T G.987.3 Annex C";
      }
      enum dot1x {
        description
          "Authentication according to IEEE 802.1x.";
        reference
          "ITU-T G.987.3 Annex D";
      }
      enum as-per-v-ani-expected {
        description
          "Authentication according to the expected configuration of
           virtual ANIs. In that case an Optical Network Unit (ONU)
           will be considered authenticated with a given virtual
           Access Network Interface (vANI) when it matches all
           expected authentication data configured in this vANI or the
           'learned-serial-number' in the vANI state data. For
           instance, if a vANI is configured with an
           'expected-serial-number' and an 'expected-registration-id',
           an ONU can be considered authenticated with this vANI only
           when it matches both the 'expected-serial-number' and the
           'expected-registration-id' of this vANI.";
      }
      enum by-management-plane {
        if-feature "bbf-xpon-types:support-unconditional-onu"
                 + "-authentication-by-mgmt-plane";
        description
          "The OLT should not even try to authenticate the ONU but
           instead should unconditionally ask the Management Plane to
           authenticate the ONU. This can be used for instance as an
           optimization - in case the operator never wants that the
           OLT does ONU authentication - to avoid that the OLT
           consumes time and processing resource to parses all of its
           vANIs for nothing.";
        reference
          "TR-489 R-OLT_2";
      }
      enum by-d-olt {
        if-feature "bbf-xpon-types:support-unconditional-onu"
                 + "-authentication-by-d-olt";
        description
          "The physical OLT (pOLT) should not even try to
           authenticate the ONU but instead should unconditionally
           ask a D-OLT software component to authenticate the ONU.";
        reference
          "TR-489 R-OLT_12";
      }
      enum loid-and-lpw {
        description
          "Authentication based on the Logical Optical Network Unit
           (ONU) ID (LOID) combined with the Logical password (LPW).";
        reference
          "ITU-T G.988 Clause 9.1.1";
      }
    }
    description
      "Method for authenticating an Optical Network Unit (ONU).";
  }

  typedef raman-mitigation-type {
    type enumeration {
      enum raman-none {
        description
          "No Raman mitigation is performed.";
      }
      enum raman-8b10b {
        description
          "For Raman mitigation, the 8B10B sublayer is introduced
           between the downstream NG-PON2 physical interface (PHY)
           adaptation interface and the optical interface.";
        reference
          "ITU-T G.989.2 Clause IX.1";
      }
      enum raman-miller {
        description
          "For Raman mitigation, Miller code is used.";
        reference
          "ITU-T G.989.2 Clause IX.2";
      }
    }
    description
      "NG-PON2 Raman mitigation coding schemes when using Radio
       Frequency (RF) video overlay.";
    reference
      "ITU-T G.989.2 Appendix IX";
  }

  typedef ip-address-or-unresolved {
    type union {
      type inet:ip-address;
      type enumeration {
        enum unresolved {
          description
            "To be used when the URL cannot be resolved into an IP
             address.";
        }
      }
    }
    description
      "A type meant for a leaf which is either an IP address or
       reflects that no IP address is available.";
  }

  typedef onu-id {
    type uint32 {
      range "0..1022";
    }
    description
      "A type meant for ONU-IDs.";
  }

  typedef onu-serial-number {
    type string {
      pattern '[ -~]{4}[0-9a-fA-F]{8}';
    }
    description
      "A type meant for the serial number of an Optical Network Unit
       (ONU). In principle, ITU-T requires ONU vendors to have an ONU
       serial number start with four letters.

       However, to cope with real world deployments, it is also
       allowed that an ONU serial number starts with any four
       printable ASCII characters.";
    reference
      "ITU-T G.984.3 Clause 9.2.4.1;
       ITU-T G.987.3 Clause 11.3.3.2;
       ITU-T G.9807.1 Clause C.11.2.6.1;
       ITU-T G.9807.1 C.11.2.6.2;
       ITU-T G.9807.1 C.11.3.4.1;
       ITU-T G.989.3 Clause 11.2.6.1;
       ITU-T G.989.3 Clause 11.2.6.2;
       ITU-T G.989.3 Clause 11.3.4.1;
       ITU-T G.9804.2 Clause 11.2.6.1;
       ITU-T G.9804.2 Clause 11.2.6.2;
       ITU-T G.9804.2 Clause 11.3.4.1";
  }

  typedef int16-or-unknown {
    type union {
      type int16;
      type enumeration {
        enum unknown {
          description
            "To be used when a numerical value could not be
             determined.";
        }
      }
    }
    description
      "A type meant for a leaf which indicates an int16 numerical
       value or that indicates that a numerical value could not be
       determined.";
  }

  typedef uint8-or-unknown {
    type union {
      type uint8;
      type enumeration {
        enum unknown {
          description
            "To be used when a numerical value could not be
             determined.";
        }
      }
    }
    description
      "A type meant for a leaf which indicates an uint8 numerical
       value or that indicates that a numerical value could not be
       determined.";
  }

  typedef onu-registration-id {
    type string {
      length "0..72";
    }
    description
      "The registration ID of an Optical Network Unit (ONU) with each
       octet represented as two hexadecimal characters.";
  }

  typedef string-ascii4-or-empty {
    type string {
      length "0..4";
      pattern '[ -~]*';
    }
    description
      "Used where a string is needed which has a maximum length of 4
       characters and also allows for a null string (length = 0).

       The character set is limited to the 95 printable ASCII
       characters.";
  }

  typedef string-ascii14-or-empty {
    type string {
      length "0..14";
      pattern '[ -~]*';
    }
    description
      "Used where a string is needed which has a maximum length of 14
       characters and also allows for a null string (length = 0).

       The character set is limited to the 95 printable ASCII
       characters.";
  }

  typedef string-ascii20-or-empty {
    type string {
      length "0..20";
      pattern '[ -~]*';
    }
    description
      "Used where a string is needed which has a maximum length of 20
       characters and also allows for a null string (length = 0).

       The character set is limited to the 95 printable ASCII
       characters.";
  }

  identity onu-ploam-enable-disable-function-base {
    description
      "Base identity used to reflects the function to be
       done to an Optical Network Unit (ONU), by means of
       a Disable_Serial_Number downstream PLOAM message.";
    reference
      "ITU-T G.984.3 clause 9.2.1;
       ITU-T G.987.3 table 11.2;
       ITU-T G.9807.1 table C11.2;
       ITU-T G.989.3 table 11-9";
  }

  identity send-ploam-to-disable-onu {
    base onu-ploam-enable-disable-function-base;
    description
      "The Optical Network Unit (ONU) is to be disabled by
       means of a Disable_Serial_Number downstream PLOAM
       message with the 'disable' option.";
  }

  identity send-ploam-to-enable-onu {
    base onu-ploam-enable-disable-function-base;
    description
      "The Optical Network Unit (ONU) is to be enabled by
       means of a Disable_Serial_Number downstream PLOAM
       message with the 'enable' option.";
  }

  identity onu-ploam-enabled-disabled-state-base {
    description
      "Base identity used to reflects the state resulting
       from the OLT sending a Disable_Serial_Number downstream
       PLOAM message to an Optical Network Unit (ONU).";
    reference
      "ITU-T G.984.3 clause 9.2.1;
       ITU-T G.987.3 table 11.2;
       ITU-T G.9807.1 table C11.2;
       ITU-T G.989.3 table 11-9";
  }

  identity onu-enabled-disabled-success-base {
    base onu-ploam-enabled-disabled-state-base;
    description
      "The OLT has successfully transmitted a
       Disable_Serial_Number downstream PLOAM message with
       to the Optical Network Unit (ONU) that was 'present'
       on the channel pair  (i.e., on a channel termination
       belonging to the channel pair).";
  }

  identity onu-has-been-disabled {
    base onu-enabled-disabled-success-base;
    description
      "The OLT has transmitted a Disable_Serial_Number downstream
       PLOAM message with the 'disable' option to the Optical
       Network Unit (ONU) that was 'present' on the channel pair
       (i.e., on a channel termination belonging to the channel
       pair).";
  }

  identity onu-has-been-re-enabled {
    base onu-enabled-disabled-success-base;
    description
      "The OLT receives again upstream messages such as a
       'Serial_Number_ ONU' PLOAM message from the Optical
       Network Unit (ONU) after it transmitted it a
       Disable_Serial_Number downstream PLOAM message with
       the 'enable' option.";
  }

  identity onu-is-to-be-disabled {
    base onu-ploam-enabled-disabled-state-base;
    description
      "The OLT has been instructed to transmit a
       Disable_Serial_Number downstream PLOAM message with
       the 'disable' option to the Optical Network Unit (ONU)
       but has not succeeded yet to do so, for instance
       because the ONU is not 'present' on the channel pair
       (i.e., on a channel termination belonging to the channel
       pair).";
  }

  identity onu-is-to-be-enabled {
    base onu-ploam-enabled-disabled-state-base;
    description
      "The OLT has transmitted one or several
       Disable_Serial_Number downstream PLOAM message(s) with
       the 'enable' option to the Optical Network Unit (ONU)
       but has not yet received any subsequent upstream traffic
       from the ONU, leading the OLT to assume that the ONU
       did not receive the PLOAM message because for instance
       it was not connected.";
  }

  identity olt-stopped-attempting-to-enable-onu {
    base onu-ploam-enabled-disabled-state-base;
    description
      "The OLT has transmitted one or several
       Disable_Serial_Number downstream PLOAM message with
       the 'enable' option to the Optical Network Unit (ONU)
       but has not yet received any subsequent upstream traffic
       from the ONU, for more than the duration of
       'onu-enable-disable-ploam-giveup-timer. Consequently,
       the OLT has stopped such attempts.";
  }

  identity olt-stopped-attempting-to-disable-onu {
    base onu-ploam-enabled-disabled-state-base;
    description
      "The OLT has been instructed to transmit a
       Disable_Serial_Number downstream PLOAM message with
       the 'disable' option to the Optical Network Unit (ONU)
       but has not succeeded yet to do so, after more than
       'onu-enable-disable-ploam-giveup-timer' duration, for
       instance because the ONU was not 'present' on the channel
       pair (i.e., on a channel termination belonging to the
       channel pair). Consequently, the OLT has stopped such
       attempts.";
  }

  typedef timer-uint32-or-disabled {
    type union {
      type uint32;
      type enumeration {
        enum disabled {
          description
            "Timer should not be started at all.";
        }
      }
    }
    description
      "Determines how long a timer will run. Value 'disabled'
       means that the timer must not be started.";
  }

  typedef alloc-id {
    type uint16;
    description
      "Transmission Container (T-CONT) Allocation Identifier
       (Alloc-ID). Unlike the 'alloc-id' type defined in module
       bbf-xpongemtcont, this type can be used in several modules
       without importing data nodes of module bbf-xpongemtcont.

       For G-PON, range is 256..4095.
       For XG-PON, range is 1024..16383.
       For XGS-PON, range is 1024..16383.
       For NG-PON2, range is 1024..16383.
       For 25GS-PON, range is 1024..16383.
       For 50G-PON, range is 1024..16383.";
    reference
      "ITU-T G.984.3 Clause 5.5.3;
       ITU-T G.987.3 Clause 6.4.3;
       ITU-T G.9807.1 Clause C.6.1.5.7;
       ITU-T G.989.3 Clause 6.1.5.7;
       ITU-T G.9804.2 Clause 6.5.2.6;
       MSA 25GS-PON Section C.6.1.5.7";
  }
}
