submodule bbf-vdsl-line-status-body {
  yang-version 1.1;
  belongs-to bbf-vdsl {
    prefix bbf-vdsl;
  }

  include bbf-vdsl-base;
  include bbf-vdsl-base-body;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing Broadband Forum TR-252i3 clause 5.1 xDSL Line.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping line-status {
    description
      "The xDSL Line status parameters represent status/state data
       nodes for an individual physical transmission line.";
    leaf xdsl-transmission-system {
      type xts-descriptor;
      description
        "This indicates the current xDSL Transmission System.";
      reference
        "ITU-T G.997.1 clause 7.3.1.1.1 (XTSE)";
    }
    leaf line-power-management-state {
      type enumeration {
        enum L0 {
          description
            "Synchronized - This line state (L0) is when
             the line has full transmission (i.e., showtime).";
        }
        enum L1 {
          description
            "Power down data transmission - This line state
             (L1) is when there is transmission on the line but the
             net data rate is reduced (e.g., only for OAM and higher
             layer connection and session control). This state
             applies to ITU-T G.992.2 only.";
        }
        enum L2 {
          description
            "Power down data transmission - This line state
             (L2) is when there is transmission on the line but the
             net data rate is reduced (e.g., only for OAM and higher
             layer connection and session control). This state
             applies to ITU-T G.992.3 and ITU-T G.992.4 only.";
        }
        enum L3 {
          description
            "No-power - This line state (L3) is when there
             is no power transmitted on the line at all.";
        }
      }
      description
        "This parameter identifies the power management state of
         the line.";
      reference
        "ITU-T G.997.1 clause 7.5.1.5";
    }
    leaf initialization-success-failure-cause {
      type enumeration {
        enum successful {
          value 0;
          description
            "Successful.";
        }
        enum config-error {
          value 1;
          description
            "Configuration error. This error occurs with
             inconsistencies in configuration parameters. For
             example, when the line is initialized in an xDSL
             transmission system where an xDSL Transceiver Unit (xTU)
             does not support the configured maximum delay or the
             configured minimum or maximum data rate for one or more
             bearer channels.";
        }
        enum config-not-feasible {
          value 2;
          description
            "Configuration not feasible on the line. This error
             occurs if the minimum data rate cannot be reached on
             the line with the minimum noise margin, maximum Power
             Spectral Density (PSD) level, maximum delay and maximum
             bit error ratio for one or more bearer channels.";
        }
        enum communication-problem {
          value 3;
          description
            "Communication problem. This error occurs, for example,
             due to corrupted messages or bad syntax messages or if
             no common mode can be selected in the G.994.1
             handshaking procedure or due to a timeout.";
        }
        enum no-far-end-xtu-detected {
          value 4;
          description
            "No peer xDSL Transceiver Unit (xTU) detected. This error
             occurs if the peer xTU is not powered or not connected or
             if the line is too long to allow detection of a peer
             xTU.";
        }
        enum unknown {
          value 5;
          description
            "Any other or unknown initialization failure cause.";
        }
        enum rtx-not-selected {
          value 6;
          description
            "ITU T G.998.4 retransmission mode was not selected
             while RTX_MODE = FORCED or with
             RTX_MODE = RTX_TESTMODE.";
        }
      }
      description
        "This parameter indicates whether the last full
         initialization procedure was successful. If the last
         initialization procedure was not successful, this
         parameter provides the reason.";
      reference
        "ITU-T G.997.1 clause 7.5.1.6";
    }
    leaf vdsl2-lr-actual-op-type {
      if-feature "bbf-vdsl:vdsl2-lr";
      type enumeration {
        enum disabled {
          description
            "Operation according to VDSL2 Long Reach (VDSL2-LR) mode
             is disabled.";
        }
        enum short {
          description
            "Operating according to VDSL2 Long Reach (VDSL2-LR) short
             loop operation type.";
        }
        enum medium {
          description
            "Operation according to VDSL2 Long Reach (VDSL2-LR) medium
             loop operation type.";
        }
        enum long {
          description
            "Operation according to VDSL2 Long Reach (VDSL2-LR) long
             loop operation type.";
        }
      }
      description
        "This parameter reports the actual operation type
         of the VDSL2 Long Reach (VDSL2-LR) mode.";
      reference
        "ITU-T G.997.1 clause 7.5.1.44.1 (VDSL2-LR_ACTOPTYPE)";
    }
  }
}
