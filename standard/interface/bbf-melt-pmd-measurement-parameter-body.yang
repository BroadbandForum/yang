submodule bbf-melt-pmd-measurement-parameter-body {
  yang-version 1.1;
  belongs-to bbf-melt {
    prefix bbf-melt;
  }

  include bbf-melt-pmd-profile-body;
  include bbf-melt-base;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     Metallic Line Test Physical Medium Dependent (MELT-PMD)
     measurement parameters.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  identity melt-cdcr {
    base measurement-class;
    description
      "The 4-element DC resistance with controlled metallic
       voltage.";
    reference
      "ITU-T G.996.2 clause E.2.3.1 (MELT-CDCR-xx)";
  }

  identity melt-cc {
    base measurement-class;
    description
      "The 3-element capacitance with controlled metallic voltage.";
    reference
      "ITU-T G.996.2 clause E.2.3.4 (MELT-CC-xx)";
  }

  identity melt-fvdc {
    base measurement-class;
    description
      "The foreign DC voltage.";
    reference
      "ITU-T G.996.2 clause E.2.3.5 (MELT-FVDC-xx)";
  }

  identity melt-fvac {
    base measurement-class;
    description
      "The foreign AC voltage.";
    reference
      "ITU-T G.996.2 clause E.2.3.5 (MELT-FVAC-xx)";
  }

  identity melt-hc {
    base measurement-class;
    description
      "The loop capacitance.";
    reference
      "ITU-T G.996.2 clause E.2.3.6 (MELT-HC-xx)";
  }

  identity melt-hdcr {
    base measurement-class;
    description
      "The loop resistance with high metallic voltage.";
    reference
      "ITU-T G.996.2 clause E.2.3.7 (MELT-HDCR-xx)";
  }

  identity melt-ca {
    base measurement-class;
    description
      "The 3-element complex admittance with controlled metallic
       voltage.";
    reference
      "ITU-T G.996.2 clause E.2.3.9 (MELT-CAx-xx)";
  }

  identity melt-ha {
    base measurement-class;
    description
      "The loop complex admittance with high metallic voltage.";
    reference
      "ITU-T G.996.2 clause E.2.3.10 (MELT-HAx-xx)";
  }

  typedef four-element-dc-resistance {
    type uint32 {
      range "0..10000000";
    }
    units "ohms";
    description
      "The 4-element DC resistances, RTR (Tip-to-Ring), RRT
       (Ring-to-Tip), RTG (Tip-to-Ground), and RRG (Ring-to-Ground),
       shall be represented in linear format. The range of valid
       values is from 0 to 10 megaohms with a granularity of 1 ohm.";
    reference
      "ITU-T G.996.2 clause E.2.3.1 (MELT-CDCR-TR, MELT-CDCR-RT,
       MELT-CDCR-TG, MELT-CDCR-RG)";
  }

  typedef three-element-capacitance {
    type int32 {
      range "-20000..50000" {
        description
          "Defines a range from 2000.0 to 5000.0 nanofarads.";
      }
    }
    units "0.1 nanofarads";
    description
      "The 3-element capacitances, CTR (Tip-to-Ring), CTG
       (Tip-to-Ground), and CRG (Ring-to-Ground), shall be represented
       in linear format. The range of valid values is from -2 to 5
       microfarads with a granularity of 0.1 nanofarads.";
    reference
      "ITU-T G.996.2 clause E.2.3.4 (MELT-CC-TR, MELT-CC-TG,
       MELT-CC-RG)";
  }

  typedef foreign-dc-voltage {
    type int16 {
      range "-3500..3500" {
        description
          "Defines a range from -350.0 to 350.0 volts.";
      }
    }
    units "0.1 volts";
    description
      "The range of valid values for the foreign DC voltages,
       VTR-DC (Tip-to-Ring), VTG-DC (Tip-to-Ground), and VRG-DC
       (Ring-to-Ground) is from -350 to 350 volts. The foreign DC
       voltage shall be represented in linear format with a
       granularity of 100 millivolts.

       The reported DC voltage polarity is defined with respect to
       ground for the VTG-DC and VRG-DC measurements and returns a
       positive result for the VTR-DC measurement if the tip wire
       is more positive than the ring wire.";
    reference
      "ITU-T G.996.2 clause E.2.3.5 (MELT-FVDC-TR, MELT-FVDC-TG,
       MELT-FVDC-RG)";
  }

  typedef foreign-ac-voltage {
    type uint16 {
      range "0..2500" {
        description
          "Defines a range from 0.0 to 250.0 volts RMS.";
      }
    }
    units "0.1 volts RMS";
    description
      "The range of valid values for the foreign AC voltages
       VTR-AC (Tip-to-Ring), VTG-AC (Tip-to-Ground), and VRG-AC
       (Ring-To-Ground) is from 0 to 250 volts RMS. The foreign AC
       voltage shall be represented in linear format with a
       granularity of 100 millivolts.";
    reference
      "ITU-T G.996.2 clause E.2.3.5 (MELT-FVAC-TR, MELT-FVAC-TG,
       MELT-FVAC-RG)";
  }

  typedef foreign-ac-voltage-frequency {
    type uint16 {
      range "100..900" {
        description
          "Defines a range from 10.0 to 90.0 Hz.";
      }
    }
    units "0.1 Hz";
    description
      "The range of valid values for the foreign AC voltage FTR-AC
       (Tip-to-Ring), FTG-AC (Tip-to-Ground), and FRG-AC
       (Ring-To-Ground) is from 10 to 90 Hz with a granularity
       of 0.1 Hz.";
    reference
      "ITU-T G.996.2 clause E.2.3.5 (MELT-FVACF-TR, MELT-FVACF-TG,
       MELT-FVACF-RG)";
  }

  typedef loop-resistance {
    type uint32 {
      range "0..10000000";
    }
    units "ohms";
    description
      "The loop resistances RTF-HV (Tip-to-Ring) and RRT-HV
       (Ring-to-Tip) shall be represented in linear format. The range
       of valid values is from 0 to 10 megaohms with a granularity of
       1 ohm. The RTR-HV and RRT-HV values of the loop resistance with
       high metallic voltage test are the total resistances measured.
       The RTR and RRT values obtained from the 3-element resistance
       with controlled metallic voltage test are not subtracted from
       the results.";
    reference
      "ITU-T G.996.2 clause E.2.3.7 (MELT-HDCR-TR, MELT-HDCR-RT)";
  }

  typedef dc-test-voltage {
    type int16 {
      range "-1500..1500" {
        description
          "Defines a range from -150.0 to 150.0 volts.";
      }
    }
    units "0.1 volts";
    description
      "The test voltages for the measurement of the 4-element DC
       resistance, VDCTR (Tip-to-Ring), VDCRT (Ring-to-Tip), VDCTG
       (Tip-to-Ground), and VDCRG (Ring-to-Ground), shall be
       represented in linear format. The range of valid values is from
       -150 V to +150 volts with a granularity of 0.1 volts.";
    reference
      "ITU-T G.996.2 clause E.2.3.2 (MELT-CDCV-TR, MELT-CDCV-RT,
       MELT-CDCV-TG, MELT-CDCV-RG)";
  }

  typedef test-current {
    type int32 {
      range "-1000000..1000000";
    }
    units "microamperes";
    description
      "The test currents for the measurement of the 4-element DC
       resistance, IDCTR (Tip-to-Ring), IDCRT (Ring-to-Tip),
       IDCTG (Tip-to-Ground), and IDCRG (Ring-to-Ground), shall be
       represented in linear format. The range of valid values is from
       -1 A to +1 ampere with a granularity of 1 microampere.";
    reference
      "ITU-T G.996.2 clause E.2.3.3 (MELT-CDCI-TR, MELT-CDCI-RT,
       MELT-CDCI-TG, MELT-CDCI-RG)";
  }

  typedef loop-resistance-test-voltage {
    type int16 {
      range "-1500..1500" {
        description
          "Defines a range from -150.0 to 150.0 volts.";
      }
    }
    units "0.1 volts";
    description
      "The test voltages for the measurement of the loop resistance
       with a high metallic voltage, VDCHTR (Tip-to-Ring) and
       VDCHRT (Ring-to-Tip) shall be represented in linear format.
       The range of valid values is from -150 volts to +150 volts with
       a granularity of 0.1 volts.";
    reference
      "ITU-T G.996.2 clause E.2.3.8 (MELT-HDCV-TR, MELT-HDCV-RT)";
  }

  typedef measurement-voltage {
    type uint16 {
      range "0..1500" {
        description
          "Defines a range from -150.0 to 150.0 volts.";
      }
    }
    units "0.1 volts";
    description
      "The range of valid values for the AC voltages VACTR-CC
       (Tip-to-Ring), VACTG-CC (Tip-to-Ground), and VACRG-CC
       (Ring-to-Ground) for the 3-element capacitance test with
       a controlled metallic voltage is from 0 volts RMS to 150 volts
       RMS. The values shall be represented in linear format with a
       granularity of 0.1 volts.

       The range of valid values for the AC voltage VACTR-HC for the
       loop capacitance test with a high metallic voltage is from 0
       volts RMS to 150 volts RMS. The values shall be represented in
       linear format with a granularity of 0.1 volts.

       The range of valid values for the AC voltages VACTR-CA,
       VACTG-CA, and VACRG-CA for the 3-element complex admittance
       test with a controlled metallic voltage is from 0 volts RMS to
       150 volts RMS. The values shall be represented in linear format
       with a granularity of 0.1 volts.

       The range of valid values for the AC voltage VACTR-HA for the
       loop complex admittance test with a high metallic voltage is
       from 0 volts RMS to 150 volts RMS. The values shall be
       represented in linear format with a granularity of 0.1 volts.";
    reference
      "ITU-T G.996.2 clauses E.2.3.11 (MELT-ACV-CC-TR,
       MELT-ACV-CC-TG, MELT-ACV-CC-RG); E.2.3.12 (MELT-ACV-HC-TR);
       E.2.3.13 (MELT-ACV-CA-TR, MELT-ACV-CA-TG, MELT-ACV-CA-RG);
       E.2.3.14 (MELT-ACV-HA-TR); and E.2.2.3 (MELT-HCA-V)";
  }

  typedef complex-admittance {
    type uint32 {
      range "1..1000000" {
        description
          "Defines a range from 0.1 to 100000.0 microsiemens.";
      }
    }
    units "0.1 microsiemens";
    description
      "The range of valid values for the 3-element complex
       conductances and susceptances, GTR and BTR (Tip-to-Ring);
       GTG and BTG (Tip-to-Ground); and GRG and BRG (Ring-to-Ground)
       is from 0.1 microsiemens to 0.1 siemens. The values shall be
       represented in linear format with a granularity of 0.1
       microsiemens.

       NOTE - The linear format is chosen for simplicity reason and
       does not imply any future accuracy requirements.";
    reference
      "ITU-T G.996.2 clause E.2.3.9 (MELT-CAG-TR, MELT-CAB-TR,
       MELT-CAG-TG, MELT-CAB-TG, MELT-CAG-RG, MELT-CAB-RG)";
  }

  typedef loop-complex-admittance {
    type uint32 {
      range "1..1000000" {
        description
          "Defines a range from 0.1 to 100000.0 microsiemens.";
      }
    }
    units "0.1 microsiemens";
    description
      "The range of valid values for the 3-element complex
       conductance and susceptance GTR,HV and BTR,HV (Tip-to-Ring) is
       from 0.1 microsiemens to 0.1 siemens. The values shall be
       represented in linear format with a granularity of 0.1
       microsiemens. The GTR,HV and BTR,HV values of the loop complex
       admittance with high metallic voltage test are the total
       conductance and susceptance measured. The GTR and BTR values
       obtained from the 3-element complex admittance with controlled
       metallic voltage test are not subtracted from the results.

       NOTE - The linear format is chosen for simplicity reason and
       does not imply any future accuracy requirements.";
    reference
      "ITU-T G.996.2 clause E.2.3.10 (MELT-HAG-TR, MELT-HAB-TR)";
  }

  typedef melt-pmd-measurement-parameter {
    type enumeration {
      enum four-element-dc-resistance-tr {
        description
          "The 4-element DC resistance with controlled metallic
           voltage, RTR (Tip-to-Ring).";
        reference
          "ITU-T G.996.2 clause E.2.3.1 (MELT-CDCR-TR)";
      }
      enum four-element-dc-resistance-rt {
        description
          "The 4-element DC resistance with controlled metallic
           voltage, RRT (Ring-to-Tip).";
        reference
          "ITU-T G.996.2 clause E.2.3.1 (MELT-CDCR-RT)";
      }
      enum four-element-dc-resistance-tg {
        description
          "The 4-element DC resistance with controlled metallic
           voltage, RTG (Tip-to-Ground).";
        reference
          "ITU-T G.996.2 clause E.2.3.1 (MELT-CDCR-TG)";
      }
      enum four-element-dc-resistance-rg {
        description
          "The 4-element DC resistance with controlled metallic
           voltage, RRG (Ring-to-Ground).";
        reference
          "ITU-T G.996.2 clause E.2.3.1 (MELT-CDCR-RG)";
      }
      enum three-element-capacitance-tr {
        description
          "The 3-element capacitance with controlled metallic
           voltage, CTR (Tip-to-Ring).";
        reference
          "ITU-T G.996.2 clause E.2.3.4 (MELT-CC-TR)";
      }
      enum three-element-capacitance-tg {
        description
          "The 3-element capacitance with controlled metallic
           voltage, CTG (Tip-to-Ground).";
        reference
          "ITU-T G.996.2 clause E.2.3.4 (MELT-CC-TG)";
      }
      enum three-element-capacitance-rg {
        description
          "The 3-element capacitance with controlled metallic
           voltage, CRG (Ring-to-Ground).";
        reference
          "ITU-T G.996.2 clause E.2.3.4 (MELT-CC-RG)";
      }
      enum foreign-dc-voltage-tr {
        description
          "The foreign DC voltage, VTR-DC (Tip-to-Ring).";
        reference
          "ITU-T G.996.2 clause E.2.3.5 (MELT-FVDC-TR)";
      }
      enum foreign-dc-voltage-tg {
        description
          "The foreign DC voltage, VTG-DC (Tip-to-Ground).";
        reference
          "ITU-T G.996.2 clause E.2.3.5 (MELT-FVDC-TG)";
      }
      enum foreign-dc-voltage-rg {
        description
          "The foreign DC voltage, VRG-DC (Ring-to-Ground).";
        reference
          "ITU-T G.996.2 clause E.2.3.5 (MELT-FVDC-RG)";
      }
      enum foreign-ac-voltage-tr {
        description
          "The foreign AC voltage, VTR-AC (Tip-to-Ring).";
        reference
          "ITU-T G.996.2 clause E.2.3.5 (MELT-FVAC-TR)";
      }
      enum foreign-ac-voltage-tg {
        description
          "The foreign AC voltage, VTG-AC (Tip-to-Ground).";
        reference
          "ITU-T G.996.2 clause E.2.3.5 (MELT-FVAC-TG)";
      }
      enum foreign-ac-voltage-rg {
        description
          "The foreign AC voltage, VRG-AC (Ring-to-Ground).";
        reference
          "ITU-T G.996.2 clause E.2.3.5 (MELT-FVAC-RG)";
      }
      enum foreign-ac-voltage-frequency-tr {
        description
          "The foreign AC voltage frequency for VTR-AC
           (Tip-to-Ring).";
        reference
          "ITU-T G.996.2 clause E.2.3.5 (MELT-FVACF-TR)";
      }
      enum foreign-ac-voltage-frequency-tg {
        description
          "The foreign AC voltage frequency for VTG-AC
           (Tip-to-Ground).";
        reference
          "ITU-T G.996.2 clause E.2.3.5 (MELT-FVACF-TG)";
      }
      enum foreign-ac-voltage-frequency-rg {
        description
          "The foreign AC voltage frequency for VRG-AC
           (Ring-to-Ground).";
        reference
          "ITU-T G.996.2 clause E.2.3.5 (MELT-FVACF-RG)";
      }
      enum loop-capacitance-hv-tr {
        description
          "The loop capacitance CTR-HV (Tip-to-Ring) shall be
           represented in linear format. The range of valid values
           is from 0 to 5 microfarads with a granularity of 0.1
           nanofarads. The CTR-HV value of the loop capacitance with
           high metallic voltage test is the total capacitance
           measured. The CTR value obtained from the 3-element
           capacitance with controlled metallic voltage test is not
           subtracted from the results.";
        reference
          "ITU-T G.996.2 clause E.2.3.6 (MELT-HV-TR)";
      }
      enum loop-resistance-hv-tr {
        description
          "The loop resistance with high metallic voltage, RTR-HV
           (Tip-to-Ring).";
        reference
          "ITU-T G.996.2 clause E.2.3.7 (MELT-HDCR-TR)";
      }
      enum loop-resistance-hv-rt {
        description
          "The loop resistance with high metallic voltage, RRT-HV
           (Ring-to-Tip).";
        reference
          "ITU-T G.996.2 clause E.2.3.7 (MELT-HDCR-RT)";
      }
      enum four-element-dc-resistance-test-voltage-tr {
        description
          "The DC test voltage for the measuremnt of 4-element DC
           resistance with a controlled metallic voltage VDC-TR
           (Tip-to-Ring).";
        reference
          "ITU-T G.996.2 clause E.2.3.2 (MELT-CDCV-TR)";
      }
      enum four-element-dc-resistance-test-voltage-rt {
        description
          "The DC test voltage for the measuremnt of 4-element DC
           resistance with a controlled metallic voltage VDC-RT
           (Ring-to-Tip).";
        reference
          "ITU-T G.996.2 clause E.2.3.2 (MELT-CDCV-RT)";
      }
      enum four-element-dc-resistance-test-voltage-tg {
        description
          "The DC test voltage for the measuremnt of 4-element DC
           resistance with a controlled metallic voltage VDC-TG
           (Tip-to-Ground).";
        reference
          "ITU-T G.996.2 clause E.2.3.2 (MELT-CDCV-TG)";
      }
      enum four-element-dc-resistance-test-voltage-rg {
        description
          "The DC test voltage for the measuremnt of 4-element DC
           resistance with a controlled metallic voltage VDC-RG
           (Ring-to-Ground).";
        reference
          "ITU-T G.996.2 clause E.2.3.2 (MELT-CDCV-RG)";
      }
      enum four-element-dc-resistance-test-current-tr {
        description
          "The test current for the measuremnt of 4-element DC
           resistance with a controlled metallic voltage IDC-TR
           (Tip-to-Ring).";
        reference
          "ITU-T G.996.2 clause E.2.3.3 (MELT-CDCI-TR)";
      }
      enum four-element-dc-resistance-test-current-rt {
        description
          "The test current for the measuremnt of 4-element DC
           resistance with a controlled metallic voltage IDC-RT
           (Ring-to-Tip).";
        reference
          "ITU-T G.996.2 clause E.2.3.3 (MELT-CDCI-RT)";
      }
      enum four-element-dc-resistance-test-current-tg {
        description
          "The test current for the measuremnt of 4-element DC
           resistance with a controlled metallic voltage IDC-TG
           (Tip-to-Ground).";
        reference
          "ITU-T G.996.2 clause E.2.3.3 (MELT-CDCI-TG)";
      }
      enum four-element-dc-resistance-test-current-rg {
        description
          "The test current for the measuremnt of 4-element DC
           resistance with a controlled metallic voltage IDC-RG
           (Ring-to-Ground).";
        reference
          "ITU-T G.996.2 clause E.2.3.3 (MELT-CDCI-RG)";
      }
      enum loop-resistance-test-voltage-tr {
        description
          "The test voltage for the measurement of the loop
           resistance with a high metallic voltage VDCH-TR
           (Tip-to-Ring).";
        reference
          "ITU-T G.996.2 clause E.2.3.8 (MELT-HDCV-TR)";
      }
      enum loop-resistance-test-voltage-rt {
        description
          "The test voltage for the measurement of the loop
           resistance with a high metallic voltage VDCH-RT
           (Ring-to-Tip).";
        reference
          "ITU-T G.996.2 clause E.2.3.8 (MELT-HDCV-RT)";
      }
      enum three-element-complex-admittance-real-tr {
        description
          "The real part of the 3-element complex admittance
           with controlled metallic voltage (Tip-to-Ring).";
        reference
          "ITU-T G.996.2 clause E.2.3.9 (MELT-CAG-TR)";
      }
      enum three-element-complex-admittance-imaginary-tr {
        description
          "The imaginary part of the 3-element complex admittance
           with controlled metallic voltage (Tip-to-Ring).";
        reference
          "ITU-T G.996.2 clause E.2.3.9 (MELT-CAB-TR)";
      }
      enum three-element-complex-admittance-real-tg {
        description
          "The real part of the 3-element complex admittance
           with controlled metallic voltage (Tip-to-Ground).";
        reference
          "ITU-T G.996.2 clause E.2.3.9 (MELT-CAG-TG)";
      }
      enum three-element-complex-admittance-imaginary-tg {
        description
          "The imaginary part of the 3-element complex admittance
           with controlled metallic voltage (Tip-to-Ground).";
        reference
          "ITU-T G.996.2 clause E.2.3.9 (MELT-CAB-TG)";
      }
      enum three-element-complex-admittance-real-rg {
        description
          "The real part of the 3-element complex admittance
           with controlled metallic voltage (Ring-to-Ground).";
        reference
          "ITU-T G.996.2 clause E.2.3.9 (MELT-CAG-RG)";
      }
      enum three-element-complex-admittance-imaginary-rg {
        description
          "The imaginary part of the 3-element complex admittance
           with controlled metallic voltage (Ring-to-Ground).";
        reference
          "ITU-T G.996.2 clause E.2.3.9 (MELT-CAB-RG)";
      }
      enum loop-complex-admittance-real-hv-tr {
        description
          "The real part of the loop complex admittance with high
           metallic voltage (Tip-to-Ring).";
        reference
          "ITU-T G.996.2 clause E.2.3.10 (MELT-HAG-TR)";
      }
      enum loop-complex-admittance-imaginary-hv-tr {
        description
          "The imaginary part of the loop complex admittance with
           high metallic voltage (Tip-to-Ring).";
        reference
          "ITU-T G.996.2 clause E.2.3.10 (MELT-HAB-TR)";
      }
      enum three-element-capacitance-measurement-voltage-tr {
        description
          "The AC voltage, VACTR-CC, for the 3-element capacitance
           test with a controlled metallic voltage (Tip-to-Ring).";
        reference
          "ITU-T G.996.2 clause E.2.3.11 (MELT-ACV-CC-TR)";
      }
      enum three-element-capacitance-measurement-voltage-tg {
        description
          "The AC voltage, VACTG-CC, for the 3-element capacitance
           test with a controlled metallic voltage
           (Tip-to-Ground).";
        reference
          "ITU-T G.996.2 clause E.2.3.11 (MELT-ACV-CC-TG)";
      }
      enum three-element-capacitance-measurement-voltage-rg {
        description
          "The AC voltage, VACRG-CC, for the 3-element capacitance
           test with a controlled metallic voltage
           (Ring-to-Ground).";
        reference
          "ITU-T G.996.2 clause E.2.3.11 (MELT-ACV-CC-RG)";
      }
      enum loop-capacitance-measurement-voltage-tr {
        description
          "The AC voltage, VACTR-HC, for the loop capacitance test
           with a high metallic voltage (Tip-to-Ring).";
        reference
          "ITU-T G.996.2 clause E.2.3.12 (MELT-ACV-HC-TR)";
      }
      enum three-element-complex-admittance-measurement-voltage-tr {
        description
          "The AC voltage, VACTR-CA, for the 3-element complex
           admittance test with a controlled metallic voltage
           (Tip-to-Ring).";
        reference
          "ITU-T G.996.2 clause E.2.3.13 (MELT-ACV-CA-TR)";
      }
      enum three-element-complex-admittance-measurement-voltage-tg {
        description
          "The AC voltage, VACTG-CA, for the 3-element complex
           admittance test with a controlled metallic voltage
           (Tip-to-Ground).";
        reference
          "ITU-T G.996.2 clause E.2.3.13 (MELT-ACV-CA-TG)";
      }
      enum three-element-complex-admittance-measurement-voltage-rg {
        description
          "The AC voltage, VACRG-CA, for the 3-element complex
           admittance test with a controlled metallic voltage
           (Ring-to-Ground).";
        reference
          "ITU-T G.996.2 clause E.2.3.13 (MELT-ACV-CA-RG)";
      }
      enum loop-complex-admittance-measurement-voltage-tr {
        description
          "The AC voltage, VACTR-HA, for the loop complex admittance
           test with a high metallic voltage (Tip-to-Ring).";
        reference
          "ITU-T G.996.2 clause E.2.3.14 (MELT-ACV-HA-TR)";
      }
    }
    description
      "An enumerated list of MELT PMD measurement parameters.";
  }

  grouping pmd-measurement-parameters {
    description
      "Defines the Metallic Line Test Physical Medium Dependent
       (MELT-PMD) measurement parameters.";
    leaf four-element-dc-resistance-tr {
      type four-element-dc-resistance;
      description
        "The 4-element DC resistance with controlled metallic
         voltage, RTR (Tip-to-Ring).";
      reference
        "ITU-T G.996.2 clause E.2.3.1 (MELT-CDCR-TR)";
    }
    leaf four-element-dc-resistance-rt {
      type four-element-dc-resistance;
      description
        "The 4-element DC resistance with controlled metallic
         voltage, RRT (Ring-to-Tip).";
      reference
        "ITU-T G.996.2 clause E.2.3.1 (MELT-CDCR-RT)";
    }
    leaf four-element-dc-resistance-tg {
      type four-element-dc-resistance;
      description
        "The 4-element DC resistance with controlled metallic
         voltage, RTG (Tip-to-Ground).";
      reference
        "ITU-T G.996.2 clause E.2.3.1 (MELT-CDCR-TG)";
    }
    leaf four-element-dc-resistance-rg {
      type four-element-dc-resistance;
      description
        "The 4-element DC resistance with controlled metallic
         voltage, RRG (Ring-to-Ground).";
      reference
        "ITU-T G.996.2 clause E.2.3.1 (MELT-CDCR-RG)";
    }
    leaf three-element-capacitance-tr {
      type three-element-capacitance;
      description
        "The 3-element capacitance with controlled metallic voltage,
         CTR (Tip-to-Ring).";
      reference
        "ITU-T G.996.2 clause E.2.3.4 (MELT-CC-TR)";
    }
    leaf three-element-capacitance-tg {
      type three-element-capacitance;
      description
        "The 3-element capacitance with controlled metallic voltage,
         CTG (Tip-to-Ground).";
      reference
        "ITU-T G.996.2 clause E.2.3.4 (MELT-CC-TG)";
    }
    leaf three-element-capacitance-rg {
      type three-element-capacitance;
      description
        "The 3-element capacitance with controlled metallic voltage,
         CRG (Ring-to-Ground).";
      reference
        "ITU-T G.996.2 clause E.2.3.4 (MELT-CC-RG)";
    }
    leaf foreign-dc-voltage-tr {
      type foreign-dc-voltage;
      description
        "The foreign DC voltage, VTR-DC (Tip-to-Ring).";
      reference
        "ITU-T G.996.2 clause E.2.3.5 (MELT-FVDC-TR)";
    }
    leaf foreign-dc-voltage-tg {
      type foreign-dc-voltage;
      description
        "The foreign DC voltage, VTG-DC (Tip-to-Ground).";
      reference
        "ITU-T G.996.2 clause E.2.3.5 (MELT-FVDC-TG)";
    }
    leaf foreign-dc-voltage-rg {
      type foreign-dc-voltage;
      description
        "The foreign DC voltage, VRG-DC (Ring-to-Ground).";
      reference
        "ITU-T G.996.2 clause E.2.3.5 (MELT-FVDC-RG)";
    }
    leaf foreign-ac-voltage-tr {
      type foreign-ac-voltage;
      description
        "The foreign AC voltage, VTR-AC (Tip-to-Ring).";
      reference
        "ITU-T G.996.2 clause E.2.3.5 (MELT-FVAC-TR)";
    }
    leaf foreign-ac-voltage-tg {
      type foreign-ac-voltage;
      description
        "The foreign AC voltage, VTG-AC (Tip-to-Ground).";
      reference
        "ITU-T G.996.2 clause E.2.3.5 (MELT-FVAC-TG)";
    }
    leaf foreign-ac-voltage-rg {
      type foreign-ac-voltage;
      description
        "The foreign AC voltage, VRG-AC (Ring-to-Ground).";
      reference
        "ITU-T G.996.2 clause E.2.3.5 (MELT-FVAC-RG)";
    }
    leaf foreign-ac-voltage-frequency-tr {
      type foreign-ac-voltage-frequency;
      description
        "The foreign AC voltage frequency for VTR-AC (Tip-to-Ring).";
      reference
        "ITU-T G.996.2 clause E.2.3.5 (MELT-FVACF-TR)";
    }
    leaf foreign-ac-voltage-frequency-tg {
      type foreign-ac-voltage-frequency;
      description
        "The foreign AC voltage frequency for VTG-AC
         (Tip-to-Ground).";
      reference
        "ITU-T G.996.2 clause E.2.3.5 (MELT-FVACF-TG)";
    }
    leaf foreign-ac-voltage-frequency-rg {
      type foreign-ac-voltage-frequency;
      description
        "The foreign AC voltage frequency for VRG-AC
         (Ring-to-Ground).";
      reference
        "ITU-T G.996.2 clause E.2.3.5 (MELT-FVACF-RG)";
    }
    leaf loop-capacitance-hv-tr {
      type int32 {
        range "-20000..50000" {
          description
            "Defines a range from -2000.0 to 5000.0 nanofarads.";
        }
      }
      units "0.1 nanofarads";
      description
        "The loop capacitance CTR-HV (Tip-to-Ring) shall be
         represented in linear format. The range of valid values is
         from -2 to 5 microfarads with a granularity of 0.1
         nanofarads. The CTR-HV value of the loop capacitance with
         high metallic voltage test is the total capacitance measured.
         The CTR value obtained from the 3-element capacitance with
         controlled metallic voltage test is not subtracted from the
         results.";
      reference
        "ITU-T G.996.2 clause E.2.3.6 (MELT-HV-TR)";
    }
    leaf loop-resistance-hv-tr {
      type loop-resistance;
      description
        "The loop resistance with high metallic voltage, RTR-HV
         (Tip-to-Ring).";
      reference
        "ITU-T G.996.2 clause E.2.3.7 (MELT-HDCR-TR)";
    }
    leaf loop-resistance-hv-rt {
      type loop-resistance;
      description
        "The loop resistance with high metallic voltage, RRT-HV
         (Ring-to-Tip).";
      reference
        "ITU-T G.996.2 clause E.2.3.7 (MELT-HDCR-RT)";
    }
    leaf four-element-dc-resistance-test-voltage-tr {
      type dc-test-voltage;
      description
        "The DC test voltage for the measuremnt of 4-element DC
         resistance with a controlled metallic voltage VDC-TR
         (Tip-to-Ring).";
      reference
        "ITU-T G.996.2 clause E.2.3.2 (MELT-CDCV-TR)";
    }
    leaf four-element-dc-resistance-test-voltage-rt {
      type dc-test-voltage;
      description
        "The DC test voltage for the measuremnt of 4-element DC
         resistance with a controlled metallic voltage VDC-RT
         (Ring-to-Tip).";
      reference
        "ITU-T G.996.2 clause E.2.3.2 (MELT-CDCV-RT)";
    }
    leaf four-element-dc-resistance-test-voltage-tg {
      type dc-test-voltage;
      description
        "The DC test voltage for the measuremnt of 4-element DC
         resistance with a controlled metallic voltage VDC-TG
         (Tip-to-Ground).";
      reference
        "ITU-T G.996.2 clause E.2.3.2 (MELT-CDCV-TG)";
    }
    leaf four-element-dc-resistance-test-voltage-rg {
      type dc-test-voltage;
      description
        "The DC test voltage for the measuremnt of 4-element DC
         resistance with a controlled metallic voltage VDC-RG
         (Ring-to-Ground).";
      reference
        "ITU-T G.996.2 clause E.2.3.2 (MELT-CDCV-RG)";
    }
    leaf four-element-dc-resistance-test-current-tr {
      type test-current;
      description
        "The test current for the measuremnt of 4-element DC
         resistance with a controlled metallic voltage IDC-TR
         (Tip-to-Ring).";
      reference
        "ITU-T G.996.2 clause E.2.3.3 (MELT-CDCI-TR)";
    }
    leaf four-element-dc-resistance-test-current-rt {
      type test-current;
      description
        "The test current for the measuremnt of 4-element DC
         resistance with a controlled metallic voltage IDC-RT
         (Ring-to-Tip).";
      reference
        "ITU-T G.996.2 clause E.2.3.3 (MELT-CDCI-RT)";
    }
    leaf four-element-dc-resistance-test-current-tg {
      type test-current;
      description
        "The test current for the measuremnt of 4-element DC
         resistance with a controlled metallic voltage IDC-TG
         (Tip-to-Ground).";
      reference
        "ITU-T G.996.2 clause E.2.3.3 (MELT-CDCI-TG)";
    }
    leaf four-element-dc-resistance-test-current-rg {
      type test-current;
      description
        "The test current for the measuremnt of 4-element DC
         resistance with a controlled metallic voltage IDC-RG
         (Ring-to-Ground).";
      reference
        "ITU-T G.996.2 clause E.2.3.3 (MELT-CDCI-RG)";
    }
    leaf loop-resistance-test-voltage-tr {
      type loop-resistance-test-voltage;
      description
        "The test voltage for the measurement of the loop resistance
         with a high metallic voltage VDCH-TR (Tip-to-Ring).";
      reference
        "ITU-T G.996.2 clause E.2.3.8 (MELT-HDCV-TR)";
    }
    leaf loop-resistance-test-voltage-rt {
      type loop-resistance-test-voltage;
      description
        "The test voltage for the measurement of the loop resistance
         with a high metallic voltage VDCH-RT (Ring-to-Tip).";
      reference
        "ITU-T G.996.2 clause E.2.3.8 (MELT-HDCV-RT)";
    }
    leaf three-element-complex-admittance-real-tr {
      type complex-admittance;
      description
        "The real part of the 3-element complex admittance
         with controlled metallic voltage (Tip-to-Ring).";
      reference
        "ITU-T G.996.2 clause E.2.3.9 (MELT-CAG-TR)";
    }
    leaf three-element-complex-admittance-imaginary-tr {
      type complex-admittance;
      description
        "The imaginary part of the 3-element complex admittance
         with controlled metallic voltage (Tip-to-Ring).";
      reference
        "ITU-T G.996.2 clause E.2.3.9 (MELT-CAB-TR)";
    }
    leaf three-element-complex-admittance-real-tg {
      type complex-admittance;
      description
        "The real part of the 3-element complex admittance
         with controlled metallic voltage (Tip-to-Ground).";
      reference
        "ITU-T G.996.2 clause E.2.3.9 (MELT-CAG-TG)";
    }
    leaf three-element-complex-admittance-imaginary-tg {
      type complex-admittance;
      description
        "The imaginary part of the 3-element complex admittance
         with controlled metallic voltage (Tip-to-Ground).";
      reference
        "ITU-T G.996.2 clause E.2.3.9 (MELT-CAB-TG)";
    }
    leaf three-element-complex-admittance-real-rg {
      type complex-admittance;
      description
        "The real part of the 3-element complex admittance
         with controlled metallic voltage (Ring-to-Ground).";
      reference
        "ITU-T G.996.2 clause E.2.3.9 (MELT-CAG-RG)";
    }
    leaf three-element-complex-admittance-imaginary-rg {
      type complex-admittance;
      description
        "The imaginary part of the 3-element complex admittance
         with controlled metallic voltage (Ring-to-Ground).";
      reference
        "ITU-T G.996.2 clause E.2.3.9 (MELT-CAB-RG)";
    }
    leaf loop-complex-admittance-real-hv-tr {
      type loop-complex-admittance;
      description
        "The real part of the loop complex admittance with high
         metallic voltage (Tip-to-Ring).";
      reference
        "ITU-T G.996.2 clause E.2.3.10 (MELT-HAG-TR)";
    }
    leaf loop-complex-admittance-imaginary-hv-tr {
      type loop-complex-admittance;
      description
        "The imaginary part of the loop complex admittance with high
         metallic voltage (Tip-to-Ring).";
      reference
        "ITU-T G.996.2 clause E.2.3.10 (MELT-HAB-TR)";
    }
    leaf three-element-capacitance-measurement-voltage-tr {
      type measurement-voltage;
      description
        "The range of valid values for the AC voltage VACTR-CC
         for the 3-element capacitance test with a controlled metallic
         voltage is from 0 volts RMS to 150 volts RMS. The values
         shall be represented in linear format with a granularity of
         0.1 volts.";
      reference
        "ITU-T G.996.2 clause E.2.3.11 (MELT-ACV-CC-TR)";
    }
    leaf three-element-capacitance-measurement-voltage-tg {
      type measurement-voltage;
      description
        "The range of valid values for the AC voltage VACTG-CC
         for the 3-element capacitance test with a controlled metallic
         voltage is from 0 volts RMS to 150 volts RMS. The values
         shall be represented in linear format with a granularity of
         0.1 volts.";
      reference
        "ITU-T G.996.2 clause E.2.3.11 (MELT-ACV-CC-TG)";
    }
    leaf three-element-capacitance-measurement-voltage-rg {
      type measurement-voltage;
      description
        "The range of valid values for the AC voltage VACRG-CC
         for the 3-element capacitance test with a controlled metallic
         voltage is from 0 volts RMS to 150 volts RMS. The values
         shall be represented in linear format with a granularity of
         0.1 volts.";
      reference
        "ITU-T G.996.2 clause E.2.3.11 (MELT-ACV-CC-RG)";
    }
    leaf loop-capacitance-measurement-voltage-tr {
      type measurement-voltage;
      description
        "The range of valid values for the AC voltage VACTR-HC for the
         loop capacitance test with a high metallic voltage is from 0
         volts RMS to 150 volts RMS. The values shall be represented
         in linear format with a granularity of 0.1 volts.";
      reference
        "ITU-T G.996.2 clause E.2.3.12 (MELT-ACV-HC-TR)";
    }
    leaf three-element-complex-admittance-measurement-voltage-tr {
      type measurement-voltage;
      description
        "The range of valid values for the AC voltage VACTR-CA for the
         3-element complex admittance test with a controlled metallic
         voltage is from 0 volts RMS to 150 volts RMS. The values
         shall be represented in linear format with a granularity of
         0.1 volts.";
      reference
        "ITU-T G.996.2 clause E.2.3.13 (MELT-ACV-CA-TR)";
    }
    leaf three-element-complex-admittance-measurement-voltage-tg {
      type measurement-voltage;
      description
        "The range of valid values for the AC voltage VACTG-CA for the
         3-element complex admittance test with a controlled metallic
         voltage is from 0 V RMS to 150 V RMS. The values shall be
         represented in linear format with a granularity of 0.1 V.";
      reference
        "ITU-T G.996.2 clause E.2.3.13 (MELT-ACV-CA-TG)";
    }
    leaf three-element-complex-admittance-measurement-voltage-rg {
      type measurement-voltage;
      description
        "The range of valid values for the AC voltage VACRG-CA for the
         3-element complex admittance test with a controlled metallic
         voltage is from 0 volts RMS to 150 volts RMS. The values
         shall be represented in linear format with a granularity of
         0.1 volts.";
      reference
        "ITU-T G.996.2 clause E.2.3.13 (MELT-ACV-CA-RG)";
    }
    leaf loop-complex-admittance-measurement-voltage-tr {
      type measurement-voltage;
      description
        "The range of valid values for the AC voltage VACTR-HA for the
         loop complex admittance test with a high metallic voltage is
         from 0 volts RMS to 150 volts RMS. The values shall be
         represented in linear format with a granularity of 0.1
         volts.";
      reference
        "ITU-T G.996.2 clause E.2.3.14 (MELT-ACV-HA-TR)";
    }
    leaf unreliability-indicator {
      if-feature
        "bbf-melt:melt-pmd-measurement-parameter-reliability";
      type bits {
        bit four-element-dc-resistance-tr {
          description
            "The 4-element DC resistance with controlled metallic
             voltage, RTR (Tip-to-Ring).";
          reference
            "ITU-T G.996.2 clause E.2.3.1 (MELT-CDCR-TR)";
        }
        bit four-element-dc-resistance-rt {
          description
            "The 4-element DC resistance with controlled metallic
             voltage, RRT (Ring-to-Tip).";
          reference
            "ITU-T G.996.2 clause E.2.3.1 (MELT-CDCR-RT)";
        }
        bit four-element-dc-resistance-tg {
          description
            "The 4-element DC resistance with controlled metallic
             voltage, RTG (Tip-to-Ground).";
          reference
            "ITU-T G.996.2 clause E.2.3.1 (MELT-CDCR-TG)";
        }
        bit four-element-dc-resistance-rg {
          description
            "The 4-element DC resistance with controlled metallic
             voltage, RRG (Ring-to-Ground).";
          reference
            "ITU-T G.996.2 clause E.2.3.1 (MELT-CDCR-RG)";
        }
        bit three-element-capacitance-tr {
          description
            "The 3-element capacitance with controlled metallic
             voltage, CTR (Tip-to-Ring).";
          reference
            "ITU-T G.996.2 clause E.2.3.4 (MELT-CC-TR)";
        }
        bit three-element-capacitance-tg {
          description
            "The 3-element capacitance with controlled metallic
             voltage, CTG (Tip-to-Ground).";
          reference
            "ITU-T G.996.2 clause E.2.3.4 (MELT-CC-TG)";
        }
        bit three-element-capacitance-rg {
          description
            "The 3-element capacitance with controlled metallic
             voltage, CRG (Ring-to-Ground).";
          reference
            "ITU-T G.996.2 clause E.2.3.4 (MELT-CC-RG)";
        }
        bit foreign-dc-voltage-tr {
          description
            "The foreign DC voltage, VTR-DC (Tip-to-Ring).";
          reference
            "ITU-T G.996.2 clause E.2.3.5 (MELT-FVDC-TR)";
        }
        bit foreign-dc-voltage-tg {
          description
            "The foreign DC voltage, VTG-DC (Tip-to-Ground).";
          reference
            "ITU-T G.996.2 clause E.2.3.5 (MELT-FVDC-TG)";
        }
        bit foreign-dc-voltage-rg {
          description
            "The foreign DC voltage, VRG-DC (Ring-to-Ground).";
          reference
            "ITU-T G.996.2 clause E.2.3.5 (MELT-FVDC-RG)";
        }
        bit foreign-ac-voltage-tr {
          description
            "The foreign AC voltage, VTR-AC (Tip-to-Ring).";
          reference
            "ITU-T G.996.2 clause E.2.3.5 (MELT-FVAC-TR)";
        }
        bit foreign-ac-voltage-tg {
          description
            "The foreign AC voltage, VTG-AC (Tip-to-Ground).";
          reference
            "ITU-T G.996.2 clause E.2.3.5 (MELT-FVAC-TG)";
        }
        bit foreign-ac-voltage-rg {
          description
            "The foreign AC voltage, VRG-AC (Ring-to-Ground).";
          reference
            "ITU-T G.996.2 clause E.2.3.5 (MELT-FVAC-RG)";
        }
        bit foreign-ac-voltage-frequency-tr {
          description
            "The foreign AC voltage frequency for VTR-AC
             (Tip-to-Ring).";
          reference
            "ITU-T G.996.2 clause E.2.3.5 (MELT-FVACF-TR)";
        }
        bit foreign-ac-voltage-frequency-tg {
          description
            "The foreign AC voltage frequency for VTG-AC
             (Tip-to-Ground).";
          reference
            "ITU-T G.996.2 clause E.2.3.5 (MELT-FVACF-TG)";
        }
        bit foreign-ac-voltage-frequency-rg {
          description
            "The foreign AC voltage frequency for VRG-AC
             (Ring-to-Ground).";
          reference
            "ITU-T G.996.2 clause E.2.3.5 (MELT-FVACF-RG)";
        }
        bit loop-capacitance-hv-tr {
          description
            "The loop capacitance CTR-HV (Tip-to-Ring) shall be
             represented in linear format. The range of valid values
             is from 0 to 5 microfarads with a granularity of 0.1
             nanofarads. The CTR-HV value of the loop capacitance with
             high metallic voltage test is the total capacitance
             measured. The CTR value obtained from the 3-element
             capacitance with controlled metallic voltage test is not
             subtracted from the results.";
          reference
            "ITU-T G.996.2 clause E.2.3.6 (MELT-HV-TR)";
        }
        bit loop-resistance-hv-tr {
          description
            "The loop resistance with high metallic voltage, RTR-HV
             (Tip-to-Ring).";
          reference
            "ITU-T G.996.2 clause E.2.3.7 (MELT-HDCR-TR)";
        }
        bit loop-resistance-hv-rt {
          description
            "The loop resistance with high metallic voltage, RRT-HV
             (Ring-to-Tip).";
          reference
            "ITU-T G.996.2 clause E.2.3.7 (MELT-HDCR-RT)";
        }
        bit four-element-dc-resistance-test-voltage-tr {
          description
            "The DC test voltage for the measuremnt of 4-element DC
             resistance with a controlled metallic voltage VDC-TR
             (Tip-to-Ring).";
          reference
            "ITU-T G.996.2 clause E.2.3.2 (MELT-CDCV-TR)";
        }
        bit four-element-dc-resistance-test-voltage-rt {
          description
            "The DC test voltage for the measuremnt of 4-element DC
             resistance with a controlled metallic voltage VDC-RT
             (Ring-to-Tip).";
          reference
            "ITU-T G.996.2 clause E.2.3.2 (MELT-CDCV-RT)";
        }
        bit four-element-dc-resistance-test-voltage-tg {
          description
            "The DC test voltage for the measuremnt of 4-element DC
             resistance with a controlled metallic voltage VDC-TG
             (Tip-to-Ground).";
          reference
            "ITU-T G.996.2 clause E.2.3.2 (MELT-CDCV-TG)";
        }
        bit four-element-dc-resistance-test-voltage-rg {
          description
            "The DC test voltage for the measuremnt of 4-element DC
             resistance with a controlled metallic voltage VDC-RG
             (Ring-to-Ground).";
          reference
            "ITU-T G.996.2 clause E.2.3.2 (MELT-CDCV-RG)";
        }
        bit four-element-dc-resistance-test-current-tr {
          description
            "The test current for the measuremnt of 4-element DC
             resistance with a controlled metallic voltage IDC-TR
             (Tip-to-Ring).";
          reference
            "ITU-T G.996.2 clause E.2.3.3 (MELT-CDCI-TR)";
        }
        bit four-element-dc-resistance-test-current-rt {
          description
            "The test current for the measuremnt of 4-element DC
             resistance with a controlled metallic voltage IDC-RT
             (Ring-to-Tip).";
          reference
            "ITU-T G.996.2 clause E.2.3.3 (MELT-CDCI-RT)";
        }
        bit four-element-dc-resistance-test-current-tg {
          description
            "The test current for the measuremnt of 4-element DC
             resistance with a controlled metallic voltage IDC-TG
             (Tip-to-Ground).";
          reference
            "ITU-T G.996.2 clause E.2.3.3 (MELT-CDCI-TG)";
        }
        bit four-element-dc-resistance-test-current-rg {
          description
            "The test current for the measuremnt of 4-element DC
             resistance with a controlled metallic voltage IDC-RG
             (Ring-to-Ground).";
          reference
            "ITU-T G.996.2 clause E.2.3.3 (MELT-CDCI-RG)";
        }
        bit loop-resistance-test-voltage-tr {
          description
            "The test voltage for the measurement of the loop
             resistance with a high metallic voltage VDCH-TR
             (Tip-to-Ring).";
          reference
            "ITU-T G.996.2 clause E.2.3.8 (MELT-HDCV-TR)";
        }
        bit loop-resistance-test-voltage-rt {
          description
            "The test voltage for the measurement of the loop
             resistance with a high metallic voltage VDCH-RT
             (Ring-to-Tip).";
          reference
            "ITU-T G.996.2 clause E.2.3.8 (MELT-HDCV-RT)";
        }
        bit three-element-complex-admittance-real-tr {
          description
            "The real part of the 3-element complex admittance
             with controlled metallic voltage (Tip-to-Ring).";
          reference
            "ITU-T G.996.2 clause E.2.3.9 (MELT-CAG-TR)";
        }
        bit three-element-complex-admittance-imaginary-tr {
          description
            "The imaginary part of the 3-element complex admittance
             with controlled metallic voltage (Tip-to-Ring).";
          reference
            "ITU-T G.996.2 clause E.2.3.9 (MELT-CAB-TR)";
        }
        bit three-element-complex-admittance-real-tg {
          description
            "The real part of the 3-element complex admittance
             with controlled metallic voltage (Tip-to-Ground).";
          reference
            "ITU-T G.996.2 clause E.2.3.9 (MELT-CAG-TG)";
        }
        bit three-element-complex-admittance-imaginary-tg {
          description
            "The imaginary part of the 3-element complex admittance
             with controlled metallic voltage (Tip-to-Ground).";
          reference
            "ITU-T G.996.2 clause E.2.3.9 (MELT-CAB-TG)";
        }
        bit three-element-complex-admittance-real-rg {
          description
            "The real part of the 3-element complex admittance
             with controlled metallic voltage (Ring-to-Ground).";
          reference
            "ITU-T G.996.2 clause E.2.3.9 (MELT-CAG-RG)";
        }
        bit three-element-complex-admittance-imaginary-rg {
          description
            "The imaginary part of the 3-element complex admittance
             with controlled metallic voltage (Ring-to-Ground).";
          reference
            "ITU-T G.996.2 clause E.2.3.9 (MELT-CAB-RG)";
        }
        bit loop-complex-admittance-real-hv-tr {
          description
            "The real part of the loop complex admittance with high
             metallic voltage (Tip-to-Ring).";
          reference
            "ITU-T G.996.2 clause E.2.3.10 (MELT-HAG-TR)";
        }
        bit loop-complex-admittance-imaginary-hv-tr {
          description
            "The imaginary part of the loop complex admittance with
             high metallic voltage (Tip-to-Ring).";
          reference
            "ITU-T G.996.2 clause E.2.3.10 (MELT-HAB-TR)";
        }
        bit three-element-capacitance-measurement-voltage-tr {
          description
            "The AC voltage, VACTR-CC, for the 3-element capacitance
             test with a controlled metallic voltage (Tip-to-Ring).";
          reference
            "ITU-T G.996.2 clause E.2.3.11 (MELT-ACV-CC-TR)";
        }
        bit three-element-capacitance-measurement-voltage-tg {
          description
            "The AC voltage, VACTG-CC, for the 3-element capacitance
             test with a controlled metallic voltage
             (Tip-to-Ground).";
          reference
            "ITU-T G.996.2 clause E.2.3.11 (MELT-ACV-CC-TG)";
        }
        bit three-element-capacitance-measurement-voltage-rg {
          description
            "The AC voltage, VACRG-CC, for the 3-element capacitance
             test with a controlled metallic voltage
             (Ring-to-Ground).";
          reference
            "ITU-T G.996.2 clause E.2.3.11 (MELT-ACV-CC-RG)";
        }
        bit loop-capacitance-measurement-voltage-tr {
          description
            "The AC voltage, VACTR-HC, for the loop capacitance test
             with a high metallic voltage (Tip-to-Ring).";
          reference
            "ITU-T G.996.2 clause E.2.3.12 (MELT-ACV-HC-TR)";
        }
        bit three-element-complex-admittance-measurement-voltage-tr {
          description
            "The AC voltage, VACTR-CA, for the 3-element complex
             admittance test with a controlled metallic voltage
             (Tip-to-Ring).";
          reference
            "ITU-T G.996.2 clause E.2.3.13 (MELT-ACV-CA-TR)";
        }
        bit three-element-complex-admittance-measurement-voltage-tg {
          description
            "The AC voltage, VACTG-CA, for the 3-element complex
             admittance test with a controlled metallic voltage
             (Tip-to-Ground).";
          reference
            "ITU-T G.996.2 clause E.2.3.13 (MELT-ACV-CA-TG)";
        }
        bit three-element-complex-admittance-measurement-voltage-rg {
          description
            "The AC voltage, VACRG-CA, for the 3-element complex
             admittance test with a controlled metallic voltage
             (Ring-to-Ground).";
          reference
            "ITU-T G.996.2 clause E.2.3.13 (MELT-ACV-CA-RG)";
        }
        bit loop-complex-admittance-measurement-voltage-tr {
          description
            "The AC voltage, VACTR-HA, for the loop complex admittance
             test with a high metallic voltage (Tip-to-Ring).";
          reference
            "ITU-T G.996.2 clause E.2.3.14 (MELT-ACV-HA-TR)";
        }
      }
      description
        "The unreliability indicator provides the set of parameters
         whose data can be considered to be unreliable.

         Possible reasons that the data is unreliable:
           - The measurement may not have been able to run, possibly
             due to external conditions.
           - The result is not reliable as the accuracy may be
             degraded due to external conditions.";
      reference
        "ITU-T G.996.2 clause E.2.2.15 (Reliability indicator)";
    }
    container melt-pmd-measurement-vendor-specific-status {
      if-feature
        "bbf-melt:melt-pmd-measurement-parameter-reliability";
      description
        "Vendor specific status associated with each MELT
         measurement test.";
      list status {
        key "parameter";
        description
          "A list of per parameter test status.";
        leaf parameter {
          type melt-pmd-measurement-parameter;
          description
            "The MELT PMD measurement parameter.";
        }
        leaf message {
          type string;
          description
            "Vendor specific status message for each of the
             MELT PMD measurement parameters.";
        }
      }
    }
  }
}
