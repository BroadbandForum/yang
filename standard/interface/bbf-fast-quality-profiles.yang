submodule bbf-fast-quality-profiles {
  yang-version 1.1;
  belongs-to bbf-fast {
    prefix bbf-fast;
  }

  import bbf-yang-types {
    prefix bbf-yang;
  }
  include bbf-fast-base;
  include bbf-fast-fast-rate-adaptation-profile-body;
  include bbf-fast-noise-margin-profile-body;
  include bbf-fast-fast-retrain-policy-profile-body;
  include bbf-fast-retransmission-profile-body;
  include bbf-fast-vectoring-profile-body;
  include bbf-fast-impulse-noise-monitoring-profile-body;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing FAST quality profiles.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef noise-margin-profile-ref {
    type leafref {
      path "/bbf-fast:fast/bbf-fast:quality/bbf-fast:noise-margin-"
         + "profile/bbf-fast:name";
    }
    description
      "Used to reference a noise margin profile.";
  }

  typedef fast-rate-adaptation-profile-ref {
    type leafref {
      path "/bbf-fast:fast/bbf-fast:quality/bbf-fast:fast-rate-"
         + "adaptation-profile/bbf-fast:name";
    }
    description
      "Used to reference a fast rate adaptation profile.";
  }

  typedef vectoring-profile-ref {
    type leafref {
      path "/bbf-fast:fast/bbf-fast:quality/bbf-fast:vectoring-"
         + "profile/bbf-fast:name";
    }
    description
      "Used to reference a vectoring profile.";
  }

  typedef fast-retrain-policy-profile-ref {
    type leafref {
      path "/bbf-fast:fast/bbf-fast:quality/bbf-fast:fast-retrain-"
         + "policy-profile/bbf-fast:name";
    }
    description
      "Used to reference a fast retrain policy profile.";
  }

  typedef retransmission-profile-ref {
    type leafref {
      path "/bbf-fast:fast/bbf-fast:quality/bbf-fast:"
         + "retransmission-profile/bbf-fast:name";
    }
    description
      "Used to reference a retransmission profile.";
  }

  augment "/bbf-fast:fast/bbf-fast:quality" {
    description
      "Data nodes for quality-related configuration profiles.";
    list noise-margin-profile {
      key "name";
      description
        "A list of noise margin profiles.";
      leaf name {
        type bbf-yang:string-ascii64;
        description
          "A name that uniquely identifies the profile.";
      }
      uses noise-margin-profile;
    }
    list fast-rate-adaptation-profile {
      key "name";
      description
        "A list of fast rate adaptation profiles.";
      leaf name {
        type bbf-yang:string-ascii64;
        description
          "A name that uniquely identifies the profile.";
      }
      uses fast-rate-adaptation-profile;
    }
    list vectoring-profile {
      key "name";
      description
        "A list of vectoring profiles.";
      leaf name {
        type bbf-yang:string-ascii64;
        description
          "A name that uniquely identifies the profile.";
      }
      uses vectoring-profile;
    }
    list fast-retrain-policy-profile {
      key "name";
      description
        "A list of fast retrain policy profiles.";
      leaf name {
        type bbf-yang:string-ascii64;
        description
          "A name that uniquely identifies the profile.";
      }
      uses fast-retrain-policy-profile;
    }
    list retransmission-profile {
      key "name";
      description
        "A list of retransmission profiles.";
      leaf name {
        type bbf-yang:string-ascii64;
        description
          "A name that uniquely identifies the profile.";
      }
      uses retransmission-profile;
    }
    list impulse-noise-monitoring-profile {
      if-feature "bbf-fast:impulse-noise-monitoring";
      key "name";
      description
        "A list of impulse noise monitoring profiles.";
      leaf name {
        type bbf-yang:string-ascii64;
        description
          "A name that uniquely identifies the profile.";
      }
      uses impulse-noise-monitoring-profile;
    }
  }
}
