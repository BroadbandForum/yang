submodule bbf-fast-channel-performance-body {
  yang-version 1.1;
  belongs-to bbf-fast {
    prefix bbf-fast;
  }

  import bbf-yang-types {
    prefix bbf-yang;
  }
  include bbf-fast-base;
  include bbf-fast-perf-types;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of performance-related
     YANG data types and grouping definitions for the management
     of FAST bearer channels.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef error-free-bits-count {
    type uint32;
    units "65536 bits";
    description
      "Defines the typedef to be used for error-free bits
       counters.";
  }

  typedef error-free-throughput {
    type uint32;
    units "kilobits per second";
    description
      "Defines the typedef to be used for error-free throughput
       parameters.";
  }

  grouping channel-test-parameters {
    description
      "Defines channel test parameters.";
    leaf error-free-bits {
      type error-free-bits-count;
      description
        "Reports the number of error-free bits passed over the alpha
         reference point at the receiver, divided by 65536.";
      reference
        "ITU-T G.997.2 clause 7.11.5.1-7.11.5.4 (EFB-C15M,
         EFB-P15M,EFB-C24H,EFB-P24H);
         ITU-T G.9701 clause 11.4.1.1.6";
    }
    leaf minimum-error-free-throughput {
      type error-free-throughput;
      description
        "Reports the minimum error-free throughput.";
      reference
        "ITU-T G.997.2 clause 7.11.5.5-7.11.5.8 (MINEFTR-C15M,
         MINEFTR-P15M,MINEFTR-C24H,MINEFTR-P24H);
         ITU-T G.9701 clause 11.4.1.1.3";
    }
  }

  grouping channel-performance-parameters {
    description
      "Defines the performance parameters for FAST bearer
       channels.";
    uses channel-test-parameters;
    leaf code-violations {
      type bbf-yang:performance-counter32;
      description
        "Reports a count of the cyclic redundancy check anomalies
         (CRC).";
      reference
        "ITU-T G.997.2 clause 7.8.4 (CURR/PREV_NE/FE_15/24_CV);
         ITU-T G.9701 clause 11.3.1.1";
    }
    leaf uncorrected-dtus {
      type bbf-yang:performance-counter32;
      description
        "Reports a count of the uncorrected Data Transfer Unit (DTU)
         anomalies (rtx-uc).";
      reference
        "ITU-T G.997.2 clause 7.8.5 (CURR/PREV_NE/FE_15/24_RTXUC);
         ITU-T G.9701 clause 11.3.1.1";
    }
    leaf retransmitted-dtus {
      type bbf-yang:performance-counter32;
      description
        "Reports a count of the retransmitted Data Transfer Unit (DTU)
         anomalies (rtx-tx).";
      reference
        "ITU-T G.997.2 clause 7.8.6 (CURR/PREV_NE/FE_15/24_RTXTX);
         ITU-T G.9701 clause 11.3.1.1";
    }
    leaf minimum-andeftr {
      if-feature "bbf-fast:andeftr";
      type bbf-yang:data-rate32;
      description
        "Reports the minimum All NOI with Data symbols Error-Free
         Throughput Rate (ANDEFTR) over the associated time
         interval.";
      reference
        "ITU-T G.997.2 clause 7.8.9
         (MINANDEFTR_CURR/PREV_NE/FE_15/24)";
    }
    leaf maximum-andeftr {
      if-feature "bbf-fast:andeftr";
      type bbf-yang:data-rate32;
      description
        "Reports the maximum All NOI with Data symbols Error-Free
         Throughput Rate (ANDEFTR) over the associated time
         interval.";
      reference
        "ITU-T G.997.2 clause 7.8.10
         (MAXANDEFTR_CURR/PREV_NE/FE_15/24)";
    }
    leaf sum-andeftr {
      if-feature "bbf-fast:andeftr";
      type uint32;
      units "65536 bits";
      description
        "Reports the sum of All NOI with Data symbols Error-Free
         Throughput Rate (ANDEFTR) bits, divided by 65536, over the
         associated time interval.

         Note: SUMANDEFTR and ANDEFTRDS can be used to compute the
               mean of ANDEFTR.";
      reference
        "ITU-T G.997.2 clause 7.8.11
         (SUMANDEFTR_CURR/PREV_NE/FE_15/24)";
    }
  }

  grouping channel-performance-parameters-15min {
    description
      "Defines the 15 minute performance parameters for FAST bearer
       channels.";
    leaf low-andeftr-seconds {
      if-feature "bbf-fast:andeftr";
      type seconds-counter-15min;
      description
        "Reports the count of Low All NOI with Data symbols Error-Free
         Throughput Rate (ANDEFTR) seconds.";
      reference
        "ITU-T G.997.2 clause 7.8.7 (CURR/PREV_NE/FE_15_LANDEFTRS)";
    }
    leaf andeftr-defined-seconds {
      if-feature "bbf-fast:andeftr";
      type seconds-counter-15min;
      description
        "Reports the count of All NOI with Data symbols Error-Free
         Throughput Rate (ANDEFTR) defined seconds.";
      reference
        "ITU-T G.997.2 clause 7.8.8 (CURR/PREV_NE/FE_15_ANDEFTRDS)";
    }
    leaf high-utilization-seconds {
      if-feature "bbf-fast:high-utilization-seconds";
      type seconds-counter-15min;
      description
        "Reports the count of High Utilization Seconds (HUS).";
      reference
        "ITU-T G.997.2 clause T.5.1.1 (CURR/PREV_NE/FE_15_DTA_HUS);
         ITU-T G.9701 clauses T.4.2 and T.4.3";
    }
  }

  grouping channel-performance-parameters-24hr {
    description
      "Defines the 24 hour performance parameters for FAST bearer
       channels.";
    leaf low-andeftr-seconds {
      if-feature "bbf-fast:andeftr";
      type seconds-counter-24hr;
      description
        "Reports the count of Low All NOI with Data symbols Error-Free
         Throughput Rate (ANDEFTR) seconds.";
      reference
        "ITU-T G.997.2 clause 7.8.7 (CURR/PREV_NE/FE_24_LANDEFTRS)";
    }
    leaf andeftr-defined-seconds {
      if-feature "bbf-fast:andeftr";
      type seconds-counter-24hr;
      description
        "Reports the count of All NOI with Data symbols Error-Free
         Throughput Rate (ANDEFTR) defined seconds.";
      reference
        "ITU-T G.997.2 clause 7.8.8 (CURR/PREV_NE/FE_24_ANDEFTRDS)";
    }
    leaf high-utilization-seconds {
      if-feature "bbf-fast:high-utilization-seconds";
      type seconds-counter-24hr;
      description
        "Reports the count of High Utilization Seconds (HUS).";
      reference
        "ITU-T G.997.2 clause T.5.1.1 (CURR/PREV_NE/FE_24_DTA_HUS);
         ITU-T G.9701 clauses T.4.2 and T.4.3";
    }
  }

  grouping channel-performance {
    description
      "Defines the parameters required for performance
       management of FAST lines.";
    container performance {
      description
        "Performance parameters.";
      container intervals-15min {
        description
          "15 minute interval performance history.";
        container current {
          description
            "Contains the counts that are currently accumulating.";
          container ftu-o {
            description
              "Fast Transceiver Unit - central Office.";
            uses performance-history-measured-time;
            uses channel-performance-parameters;
            uses channel-performance-parameters-15min;
          }
          container ftu-r {
            description
              "Fast Transceiver Unit - Remote side.";
            uses performance-history-measured-time;
            uses channel-performance-parameters;
            uses channel-performance-parameters-15min;
          }
        }
        uses performance-15min-history-parameters;
        list history {
          key "interval-number";
          max-elements 96;
          ordered-by system;
          description
            "A history of 15 minute intervals.";
          leaf interval-number {
            type performance-15min-history-interval;
            description
              "The number of the interval relative to the current
               interval.";
          }
          container ftu-o {
            description
              "Fast Transceiver Unit - central Office.";
            uses performance-history-15min-interval-parameters;
            uses channel-performance-parameters;
            uses channel-performance-parameters-15min;
          }
          container ftu-r {
            description
              "Fast Transceiver Unit - Remote side.";
            uses performance-history-15min-interval-parameters;
            uses channel-performance-parameters;
            uses channel-performance-parameters-15min;
          }
        }
      }
      container intervals-24hr {
        if-feature "bbf-fast:performance-24hr";
        description
          "24 hour interval performance history.";
        container current {
          description
            "Contains the counts that are currently accumulating.";
          container ftu-o {
            description
              "Fast Transceiver Unit - central Office.";
            uses performance-history-measured-time;
            uses channel-performance-parameters;
            uses channel-performance-parameters-24hr;
          }
          container ftu-r {
            description
              "Fast Transceiver Unit - Remote side.";
            uses performance-history-measured-time;
            uses channel-performance-parameters;
            uses channel-performance-parameters-24hr;
          }
        }
        uses performance-24hr-history-parameters;
        list history {
          key "interval-number";
          max-elements 7;
          ordered-by system;
          description
            "A history of 24 hour intervals.";
          leaf interval-number {
            type performance-24hr-history-interval;
            description
              "The number of the interval relative to the current
               interval.";
          }
          container ftu-o {
            description
              "Fast Transceiver Unit - central Office.";
            uses performance-history-24hr-interval-parameters;
            uses channel-performance-parameters;
            uses channel-performance-parameters-24hr;
          }
          container ftu-r {
            description
              "Fast Transceiver Unit - Remote side.";
            uses performance-history-24hr-interval-parameters;
            uses channel-performance-parameters;
            uses channel-performance-parameters-24hr;
          }
        }
      }
    }
  }
}
