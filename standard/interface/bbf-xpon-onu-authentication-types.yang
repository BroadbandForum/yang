module bbf-xpon-onu-authentication-types {
  yang-version 1.1;
  namespace "urn:bbf:yang:bbf-xpon-onu-authentication-types";
  prefix bbf-xpon-onu-autht;

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on the management of
     Passive Optical Network (PON) interfaces. As such, this module
     is specific to access network equipment (e.g., BBF-specified
     Access Nodes and FTTdp DPUs).

     Specifically, this module defines YANG types used for Optical
     Network Unit (ONU) authentication and the decision to apply
     an OMCI function.

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }
  revision 2024-04-23 {
    description
      "Issue 3.
       * Approval Date:    2024-04-23.
       * Publication Date: 2024-04-23.";
    reference
      "TR-385i3: YANG Modules for PON Management
               <https://www.broadband-forum.org/technical/download/
                        TR-385_Issue-3.pdf>";
  }
  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }

  identity onu-management-config-base {
    description
      "Base identity used to reflects the expected management mode for
       an Optical Network Unit (ONU).";
  }

  identity use-vomci {
    base onu-management-config-base;
    description
      "The Optical Network Unit (ONU) should be managed via a
       virtualized OMCI (vOMCI) function.";
    reference
      "TR-489 Section 5.1;
       TR-489 Section 5.2";
  }

  identity use-eomci {
    base onu-management-config-base;
    description
      "The Optical Network Unit (ONU) should be managed via an OMCI
       function embedded in the Optical Line ermination (OLT),
       (eOMCI).";
    reference
      "TR-489 Section 5.3;
       TR-489 Section 5.4";
  }

  identity onu-management-state-base {
    description
      "Base identity used to reflect how an Optical Line Termination
       (OLT) perceives the way that a specific Optical Network Unit
       (ONU) should be managed.";
  }

  identity onu-management-mode-ok {
    base onu-management-state-base;
    description
      "The Optical Line Termination (OLT) could successfully
       determine the management mode to be applied to a specific
       Optical Network Unit (ONU).";
  }

  identity vomci-required {
    base onu-management-mode-ok;
    description
      "The Optical Line Termination (OLT) expects that a specific
       Optical Network Unit (ONU) should be managed via a virtualized
       OMCI (vOMCI) function.";
    reference
      "TR-489 Section 5.1;
       TR-489 Section 5.2";
  }

  identity eomci-in-use {
    base onu-management-mode-ok;
    description
      "The Optical Line Termination (OLT) has engaged its embedded
       OMCI function (eOMCI) to manage a specific Optical Network Unit
       (ONU).";
    reference
      "TR-489 Section 5.3;
       TR-489 Section 5.4";
  }

  identity onu-management-mode-not-ok {
    base onu-management-state-base;
    description
      "The Optical Line Termination (OLT) has found some error when
       attempting to determine the management mode to be applied to a
       specific Optical Network Unit (ONU).";
    reference
      "TR-489 Figure 6-6;
       TR-489 Figure 6-7;
       TR-489 Figure 7-2";
  }

  identity vani-management-mode-mismatch-with-requested-mode {
    base onu-management-mode-not-ok;
    description
      "The Optical Line Termination (OLT) has found a mismatch between
       the 'expected-onu-management-mode' configured on a given vANI
       and the 'requested-onu-management-mode' that it received for
       this Optical Network Unit (ONU) from an
       'report-onu-authentication-results' action.";
    reference
      "TR-489 R-OLT_9";
  }

  identity eomci-per-olt-vomci-per-mgmt-plane {
    base vani-management-mode-mismatch-with-requested-mode;
    description
      "The Optical Line Termination (OLT) has determined that a given
       ONU should be managed via eOMCI but it has received an
       'report-onu-authentication-results' action from the Management
       Plane indicating vOMCI as 'requested-onu-management-mode'.";
    reference
      "TR-489 Section 6.2.2";
  }

  identity vomci-per-olt-eomci-per-mgmt-plane {
    base vani-management-mode-mismatch-with-requested-mode;
    description
      "The Optical Line Termination (OLT) has determined that a given
       ONU should be managed via vOMCI but it has received an
       'report-onu-authentication-results' action from the Management
       Plane indicating eOMCI as 'requested-onu-management-mode'.";
    reference
      "TR-489 Section 6.2.4";
  }

  identity eomci-expected-but-missing-onu-configuration {
    base onu-management-mode-not-ok;
    description
      "The Optical Line Termination (OLT) has determined that eOMCI
       should be engaged for a given Optical Network Unit (ONU) but it
       misses data to do so, for instance the ANI or the ONU
       configuration.";
    reference
      "TR-489 R-OLT_10";
  }

  identity onu-name-mismatch-olt-mgmt-plane {
    base onu-management-mode-not-ok;
    description
      "The Optical Line Termination (OLT) has found a mismatch between
       the 'onu-name' configured on a given vANI and the 'onu-name'
       that it received for this Optical Network Unit (ONU) from an
       'report-onu-authentication-results' action.";
    reference
      "TR-489 Section 6.2.4";
  }

  identity undetermined {
    base onu-management-mode-not-ok;
    description
      "The Optical Line Termination (OLT) has not determined at this
       stage whether the Network Unit (ONU) should be managed via an
       embedded OMCI function (eOMCI) or a virtualized OMCI function
       (vOMCI).";
    reference
      "TR-489 Section 6.2.2;
       TR-489 Section 6.2.4;
       TR-489 R-OLT_3";
  }

  identity action-error-tag {
    description
      "Base identity used for defining failures with the invocation of
       an 'report-onu-authentication-results' action.";
    reference
      "TR-489 R-OLT_8";
  }

  identity parameter-error {
    base action-error-tag;
    description
      "Parameter error.";
  }

  identity onu-not-present {
    base parameter-error;
    description
      "The Optical Network Unit (ONU) is not present or not present
       anymore on the channel termination.";
  }

  identity onu-management-mode-mismatch-with-v-ani {
    base parameter-error;
    description
      "The required ONU management mode conflicts with an explicitely
       configured 'expected-onu-magement-mode' on the vANI.";
    reference
      "TR-489 Section 6.2.2;
       TR-489 Section 6.2.4";
  }

  identity onu-name-mismatch-with-v-ani {
    base parameter-error;
    description
      "The provided 'onu-name' conflicts with an explicitely
       configured 'onu-name' on the vANI.";
    reference
      "TR-489 Section 6.2.4";
  }

  identity undetermined-error {
    base action-error-tag;
    description
      "Undetermined error.";
  }

  identity onu-authentication-results-base {
    description
      "Base identity used by the management plane to report to the
       OLT the results of its ONU authentication process.";
  }

  identity onu-authentication-successful {
    base onu-authentication-results-base;
    description
      "The management plane could identify a vANI corresponding to
       the ONU. Note that if the vANI configuration in the OLT
       indicates that Secure Mutual Authentication (SMA) is required,
       the OLT will consider the ONU authenticated only after SMA
       has been successfully executed. Until then the OLT will
       consider the vANI identified by the management plane only as
       tentatively corresponding to the ONU.";
  }

  identity onu-authentication-failed {
    base onu-authentication-results-base;
    description
      "The management plane could not identify a vANI corresponding
       to the ONU.";
  }

  identity onu-pre-authentication-pending-sma-success {
    base onu-authentication-results-base;
    description
      "ONU pre-authentication could be done identifying a tentatve
       vANI. However, Secure Mutual Authentication (SMA) between the
       OLT and ONU must still be successfully executed before the ONU
       can be confirmed successfully authenticated.";
  }
}
