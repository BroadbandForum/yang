submodule bbf-fast-base {
  yang-version 1.1;
  belongs-to bbf-fast {
    prefix bbf-fast;
  }

  import ietf-interfaces {
    prefix if;
  }
  import bbf-fastdsl {
    prefix bbf-fastdsl;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing top level FAST configuration and augmenations to
     ietf-interfaces.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  feature annex-x {
    description
      "Indicates support for Annex X as defined in ITU-T G.9701.";
    reference
      "ITU-T G.9701 clause X.6.7.1 and T.2.1";
  }

  feature annex-d {
    description
      "Indicates support for Annex D as defined in ITU-T G.9701.";
    reference
      "ITU-T G.9701 clause D.5.7.2 and T.2.2.1";
  }

  feature srec {
    description
      "Indicates support for Showtime Reconfiguration (SREC) as
       defined in ITU-T G.9701 Annex R.";
    reference
      "ITU-T G.9701 Annex R";
  }

  feature dta {
    description
      "Indicates support for Dynamic Time Assignment (DTA) as defined
       in ITU-T G.9701.";
    reference
      "ITU-T G.9701 Annex X and T";
  }

  feature high-utilization-seconds {
    if-feature "dta";
    description
      "Indicates support for reporting High Utilization Seconds as
       defined in ITU-T G.9701.";
    reference
      "ITU-T G.9701 clauses T.4.2 and T.4.3";
  }

  feature andeftr {
    description
      "Indicates support for All NOI with Data symbols Error-Free
       Throughput Rate (ANDEFTR).";
  }

  feature rmcr {
    description
      "Indicates support for Robust Maintenance Channel Recovery
       (RMCR).";
  }

  feature classmask {
    description
      "Indicates support for classmask configuration.";
  }

  feature impulse-noise-monitoring {
    description
      "Indicates support for Impulse Noise Monitoring (INM).";
  }

  feature preferred-ndr {
    description
      "Indicates support for Preferred Net Data Rate.";
    reference
      "ITU-T G.997.2 clause 7.2.1.5 and 7.2.1.6";
  }

  feature rmccarmask {
    description
      "Indicates support for the Robust Managmenet Channel (RMC)
       sub-carrier mask.";
    reference
      "ITU-T G.997.2 clause 7.1.2.16 and clause 7.1.2.17;
       ITU-T G.9701 clause 7.3.1.3.";
  }

  feature tgvn {
    description
      "Indicates support for Targeted Generalized Vectoring with
       Non-active G.9701 supporting lines (TGVN).";
    reference
      "ITU-T G.997.2 clause 7.1.7.5";
  }

  container fast {
    description
      "FAST configuration.";
    container service {
      description
        "Service profile configuration.";
    }
    container spectrum {
      description
        "Spectrum profile configuration.";
    }
    container quality {
      description
        "Quality profile configuration.";
    }
    container thresholds {
      description
        "Threshold configuration.";
    }
    container vectors {
      description
        "Vectors of profiles.";
    }
  }

  augment "/if:interfaces/if:interface/bbf-fastdsl:line" {
    when "bbf-fastdsl:configured-mode = 'bbf-fastdsl:mode-fast'" {
      description
        "Applicable when G.fast mode is configured.";
    }
    description
      "Data nodes for the configuration of FAST lines.";
    container line {
      presence
        "If present, indicates the interface is configured to operate
         in FAST mode.";
      description
        "Line configuration data for FAST interfaces.";
    }
  }

  augment "/if:interfaces-state/if:interface/bbf-fastdsl:line" {
    when "bbf-fastdsl:operational-mode = 'bbf-fastdsl:mode-fast'" {
      description
        "Applicable when G.fast is the current mode of operation.";
    }
    description
      "Data nodes for the operational state of FAST lines.";
    container line {
      presence
        "If present, indicates the interface is operating in FAST
         mode.";
      description
        "Line state data for FAST interfaces.";
      container channel {
        description
          "Bearer channel state data for FAST interfaces.";
      }
    }
  }
}
