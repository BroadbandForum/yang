submodule bbf-fast-ftu-inventory-body {
  yang-version 1.1;
  belongs-to bbf-fast {
    prefix bbf-fast;
  }

  include bbf-fast-line-spectrum-profile-body;
  include bbf-fast-line-status-body;
  include bbf-fast-base;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of FTU inventory related
     YANG data types and grouping definitions for the management of
     FAST interfaces.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping ftu-inventory-parameters {
    description
      "Inventory parameters.";
    reference
      "ITU-T G.997.2 clause 7.13";
    leaf g.994.1-vendor-id {
      type binary {
        length "8";
      }
      description
        "Reports the ITU-T G.994.1 vendor ID as inserted by the
         FAST Transceiver Unit - central Office (FTU-O) or FAST
         Transceiver Unit - Remote side (FTU-R) in the ITU-T G.994.1
         CL message.";
      reference
        "ITU-T G.997.2 clauses 7.13.1.1 (FTUO_GHS_VENDOR) and
         7.13.1.2 (FTUR_GHS_VENDOR);
         ITU-T G.994.1 clause 9.3.3.1";
    }
    leaf version-number {
      type binary {
        length "0..16";
      }
      description
        "Reports the version number as inserted by the FAST
         Transceiver Unit - central Office (FTU-O) or FAST Transceiver
         Unit - Remote side (FTU-R) in the embedded operations
         channel. It is for version control and is vendor specific
         information.";
      reference
        "ITU-T G.997.2 clauses 7.13.1.3 (FTUO_VERSION) and clause
         7.13.1.4 (FTUR_VERSION);
         ITU-T G.9701 clause 11.2.2.10";
    }
    leaf self-test-result {
      type binary;
      description
        "Reports the results from the most recent self-test
         procedure, initiated at power-up The first octet of the
         self-test result is 00hex if the self-test passed and 01hex
         if the self-test failed. The interpretation of the other
         octets is vendor discretionary and can be interpreted in
         combination with the FAST Transceiver Unit - central Office
         (FTU-O) or FAST Transceiver Unit - Remote side (FTU-R) ITU-T
         G.994.1 vendor ID and system vendor ID.";
      reference
        "ITU-T G.997.2 clauses 7.13.1.5 (FTUO_SELFTEST) and clause
         7.13.1.6 (FTUR_SELFTEST);
         ITU-T G.9701 clause 12.1.2";
    }
    leaf system-vendor-id {
      type binary {
        length "8";
      }
      description
        "Reports the FAST Transceiver Unit (FTU) system vendor ID as
         inserted by the FAST Transceiver Unit - central Office
         (FTU-O) or FAST Transceiver Unit - Remote side (FTU-R) in the
         embedded operations channel.";
      reference
        "ITU-T G.997.2 clauses 7.13.2.1 (DPU_SYSTEM_VENDOR) and
         clause 7.13.2.2 (NT_SYSTEM_VENDOR);
         ITU-T G.9701 clause 11.2.2.10;
         ITU-T G.994.1 clause 9.3.3.1";
    }
    leaf system-serial-number {
      type binary {
        length "0..32";
      }
      description
        "Reports the FAST Transceiver Unit (FTU) serial number as
         inserted by the FAST Transceiver Unit - central Office
         (FTU-O) or FAST Transceiver Unit - Remote side (FTU-R) in the
         embedded operations channel. It is vendor specific
         information. The combination of system vendor ID and system
         serial number creates a unique number for each FTU system.";
      reference
        "ITU-T G.997.2 clauses 7.13.2.3 (DPU_SYSTEM_SERIALNR) and
         clause 7.13.2.4 (NT_SYSTEM_SERIALNR);
         ITU-T G.9701 clause 11.2.2.10";
    }
    leaf profiles-supported {
      type profiles;
      description
        "Reports for each profile whether the FAST Transceiver Unit
         (FTU) supports operation according to that profile.";
      reference
        "ITU-T G.997.2 clauses 7.13.1.7 (FTUO_PROFILES) and clause
         7.13.1.8 (FTUR_PROFILES);
         ITU-T G.9701 clause 6";
    }
    leaf annex-x-supported {
      if-feature "bbf-fast:annex-x";
      type boolean;
      description
        "Indicates whether Annex X is supported by the FAST
         Transceiver Unit (FTU).";
      reference
        "ITU-T G.997.2 clause T.4.1 and T.4.2
         (ANNEX_X_SUPPORT_FTU_O/R);
         ITU-T G.9701 clause X.7.1.1.1 and X.7.1.2.1.";
    }
    leaf annex-d-supported {
      if-feature "bbf-fast:annex-d";
      type boolean;
      description
        "Indicates whether Annex D is supported by the FAST
         Transceiver Unit (FTU).";
      reference
        "ITU-T G.997.2 clause T.4.4 and T.4.5
         (ANNEX_D_SUPPORT_FTU_O/R);
         ITU-T G.9701 clause D.6.1.1.1 and D.6.1.2.1.";
    }
    leaf srec-supported {
      if-feature "bbf-fast:srec";
      type boolean;
      description
        "Indicates whether Showtime Reconfiguration (SREC) is
         supported by the FAST Transceiver Unit (FTU).";
      reference
        "ITU-T G.997.2 clause 7.13.1.9 and 7.13.1.10
         (ANNEX_R_SUPPORT_FTU_O/R);
         ITU-T G.9701 Annex R.";
    }
  }

  grouping ftu-o-inventory-parameters {
    description
      "Inventory parameters applicable only to the FAST Transceiver
       Unit - central Office (FTU-O).";
    leaf vce-id {
      type union {
        type enumeration {
          enum not-in-vectored-group {
            description
              "The line is not in a vectored group.";
          }
        }
        type uint8 {
          range "1..255";
        }
      }
      description
        "For the line in a vectored group, the Vectoring Control
         Entity (VCE) ID uniquely identifies the VCE that manages and
         controls the vectored group to which the line belongs. It
         consists of one octet and valid ranges are from 1 to 255. A
         special value (not-in-vectored-group) means the line is not
         in a vectored group.";
      reference
        "ITU-T G.997.2 clause 7.13.2.5 (VCE_ID);
         ITU-T G.9701 clause 11.4.5.1.1";
    }
    leaf vce-port-index {
      type union {
        type enumeration {
          enum not-in-vectored-group {
            description
              "The line is not in a vectored group.";
          }
        }
        type vce-port-index;
      }
      description
        "For the line in a vectored group, the Vectoring Control
         Entity (VCE) port index is the physical index that uniquely
         identifies the VCE port to which the line is connected. It
         is an integer from 1 to the maximum number of lines supported
         by the VCE. The combination of VCE ID and VCE port index
         creates a unique identifier for each vectored FAST
         Transceiver Unit - central Office (FTU-O)/-R. A special value
         (not-in-vectored-group) means the line is not in a vectored
         group.";
      reference
        "ITU-T G.997.2 clause 7.13.2.6 (VCE_PORT_INDEX);
         ITU-T G.9701 clause 11.4.5.1.2";
    }
    leaf idta-supported {
      if-feature "(bbf-fast:dta and bbf-fast:annex-x)";
      type boolean;
      description
        "Indicates whether independent Dynamic Time Assignment (iDTA)
         is supported by the FAST Transceiver Unit - central Office
         (FTU-O).";
      reference
        "ITU-T G.997.2 clause T.4.3 (DTA_SUPPORT_FTU_O);
         ITU-T G.9701 clause X.7.1.1.1";
    }
  }

  grouping ftu-inventory {
    description
      "Nodes defining the structure and content of FTU inventory.";
    container ftu-o {
      description
        "Inventory parameters reported by the FAST Transceiver Unit -
         central Office (FTU-O).";
      uses ftu-inventory-parameters;
      uses ftu-o-inventory-parameters;
    }
    container ftu-r {
      description
        "Inventory parameters reported by the FAST Transceiver Unit -
         Remote side (FTU-R).";
      uses ftu-inventory-parameters;
    }
  }
}
