module bbf-xponani-onu-auto-detection {
  yang-version 1.1;
  namespace "urn:bbf:yang:bbf-xponani-onu-auto-detection";
  prefix bbf-xponani-onu-ad;

  import ietf-interfaces {
    prefix if;
  }
  import bbf-xponani {
    prefix bbf-xponani;
  }
  import bbf-xpon-types {
    prefix bbf-xpon-types;
  }
  import bbf-xpon-onu-auto-detection-common {
    prefix bbf-xpon-onu-adc;
  }

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on the management of
     Passive Optical Network (PON) interfaces. As such, this module
     is specific to access network equipment (e.g., BBF-specified
     Access Nodes and FTTdp DPUs).

     Specifically, this module defines Access Network Interface (ANI)
     data nodes used for the auto-detection of the xPON type of an
     Optical Network Unit (ONU).

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }

  augment "/if:interfaces/if:interface/bbf-xponani:ani" {
    description
      "Access Network Interface (ANI) configuration data for the
       auto-detection of the xPON type of an Optical Network Unit
       (ONU).";
    container auto-detection {
      if-feature "bbf-xpon-onu-adc:onu-xpontype-auto-detection";
      presence
        "Enables the management of auto-detection of the xPON type of
         the ONU.";
      description
        "Access Network Interface (ANI) configuration data for the
         auto-detection of the xPON type of an Optical Network Unit
         (ONU).";
      list onu-id {
        if-feature "bbf-xponani:configurable-ani-onu-id";
        must 'not(../../bbf-xponani:onu-id)' {
          error-message
            "xPON type specific ONU IDs cannot be configured when "
          + "the non-xPON type specific 'onu-id' data node is "
          + "already configured.";
        }
        key "xpon-type";
        description
          "An ONU ID that can be used for a specific xPON type.";
        leaf xpon-type {
          type identityref {
            base bbf-xpon-types:xpon-type-base;
          }
          description
            "The xPON type of the ONU that is acceptable.";
        }
        leaf onu-id {
          type bbf-xpon-types:onu-id;
          description
            "This is the Transmission Convergence (TC) layer ONU-ID
             identifier. When configured, this is the value which
             the Optical Line Termination (OLT) must assign to an
             Optical Network Unit (ONU) during the ONU's activation
             using the Assign_ONU-ID PLOAM message.

             For G-PON, range is 0..253.
             For XG-PON, range is 0..1022.
             For XGS-PON, range is 0..1020.
             For NG-PON2, range is 0..1020.
             For 25GS-PON, range is 0..1018.
             For 50G-PON, range is 0..1019.";
          reference
            "ITU-T G.984.3 Clause 5.5.2;
             ITU-T G.987.3 Clause 6.4.2;
             ITU-T G.9807.1 Clause C.6.1.5.6;
             ITU-T G.989.3 Clause 6.1.5.6;
             ITU-T G.9804.2 Clause 6.5.2.5;
             MSA 25GS-PON Section C.6.1.5.7";
        }
      }
    }
  }
}
