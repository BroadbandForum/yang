submodule bbf-fast-update-test-body {
  yang-version 1.1;
  belongs-to bbf-fast {
    prefix bbf-fast;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing test updates.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef near-end-test-groups {
    type bits {
      bit group1 {
        description
          "If present, forces an update of the test parameters in
           group 1.";
      }
      bit group2 {
        description
          "If present, forces an update of the test parameters in
           group 2. Upon a request to update the XLOG test
           parameters, the xlogps values are updated for all
           disturber lines at the same time.";
      }
    }
    description
      "A set of bits representing each of the near end test groups.";
  }

  typedef far-end-test-groups {
    type bits {
      bit group1 {
        description
          "If present, forces an update of the test parameters in
           group 1.";
      }
      bit group2 {
        description
          "If present, forces an update of the test parameters in
           group 2.";
      }
    }
    description
      "A set of bits representing each of the far end test groups.";
  }

  grouping line-update-test-parameters {
    description
      "Data nodes used to update test parameters on a line.";
    container ftu-o {
      description
        "Relative to the Fast Transceiver Unit - central Office
         (FTU-O).";
      leaf update-ne-test {
        type near-end-test-groups;
        default "";
        status deprecated;
        description
          "Forces an update of the test parameters that can be
           updated during showtime. See introductory text to clause
           7.

           A configuration change back to clear a bit is required
           before initiating another update.";
        reference
          "ITU-T G.997.2 clause 7.1.9.1 (UPDATE-NE-TEST);
           ITU-T G.9701 clause 11.1";
      }
      action update-near-end-test {
        description
          "Forces an update of the test parameters that can be
           updated during showtime.";
        reference
          "ITU-T G.997.2 clause 7.1.9.1 (UPDATE-NE-TEST);
           ITU-T G.9701 clause 11.1";
        input {
          leaf group {
            type near-end-test-groups;
            must 'boolean(.)' {
              error-message "No near end test groups were specified.";
              description
                "At least one bit must be specified.";
            }
            description
              "Specifies which group or groups should be updated.";
          }
        }
      }
    }
    container ftu-r {
      description
        "Relative to the Fast Transceiver Unit - Remote side
         (FTU-R).";
      leaf update-fe-test {
        type far-end-test-groups;
        default "";
        status deprecated;
        description
          "Forces an update of the test parameters that can be
           updated during showtime. See introductory text to clause
           7.

           A configuration change back to clear a bit is required
           before initiating another update.";
        reference
          "ITU-T G.997.2 clause 7.1.9.2 (UPDATE-FE-TEST);
           ITU-T G.9701 clause 11.1";
      }
      action update-far-end-test {
        description
          "Forces an update of the test parameters that can be
           updated during showtime.";
        reference
          "ITU-T G.997.2 clause 7.1.9.2 (UPDATE-FE-TEST);
           ITU-T G.9701 clause 11.1";
        input {
          leaf group {
            type far-end-test-groups;
            must 'boolean(.)' {
              error-message "No far end test groups were specified.";
              description
                "At least one bit must be specified.";
            }
            description
              "Specifies which group or groups should be updated.";
          }
        }
      }
    }
  }
}
