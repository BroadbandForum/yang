module bbf-vlan-sub-interface-profiles {
  yang-version 1.1;
  namespace "urn:bbf:yang:bbf-vlan-sub-interface-profiles";
  prefix bbf-vsi-prof;

  import bbf-yang-types {
    prefix bbf-yang;
  }
  import bbf-if-type {
    prefix bbfift;
  }
  import ietf-interfaces {
    prefix if;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on the management of
     sub-interfaces as applicable to access network equipment. As
     such, this module is specific to access network equipment (e.g.,
     BBF-specified Access Nodes and FTTdp DPUs).

     Specifically, this module extends the methods for configuring a
     VLAN sub-interface with a method that enables management of the
     configuration through a profile.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a6; see
     the TR itself for full legal notices.";

  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }

  container vsi-profiles {
    description
      "Configuration of VLAN sub-interface profiles.";
    list vsi-profile {
      key "name";
      description
        "A profile providing a mechanism to configure data for VLAN
         sub-interfaces.

         Data nodes configured in a VLAN sub-interface profile are to
         be applied to VLAN sub-interfaces that reference the VLAN
         sub-interface profile where they get the same meaning as if
         the data was configured directly on the VLAN sub-interface.";
      leaf name {
        type bbf-yang:string-ascii64;
        description
          "The name of the profile.";
      }
      choice frame-processing {
        description
          "Configuring frame processing for a VLAN sub-interface is
           possible with one of multiple alternatives. They all have
           in common that the definition of the frame processing is
           relative to the lower-layer interface configured in the
           VLAN sub-interface its leaf 'subif-lower-layer'.

           For example, if there is configuration for ingress frame
           processing, then this means that frames received on the
           referenced lower-layer interface are subject to evaluation
           using the criteria configured.

           Not configuring any frame processing implies that there are
           no ingress match criteria to select frames received from
           the lower-layer interface into this sub-interface, and
           hence this sub-interface will not have to process any
           ingress frame.";
      }
    }
  }

  augment "/if:interfaces/if:interface" {
    when
      "derived-from-or-self(if:type, 'bbfift:vlan-sub-interface')" {
      description
        "Common optional data for VLAN sub-interfaces.";
    }
    description
      "Add data nodes for a VLAN sub-interface.";
    container vsi-profile {
      presence
        "Presence indicates a VLAN sub-interface profile is to be
         applied.";
      description
        "Data nodes for when a VLAN sub-interface profile is to be
         applied.

         Note that from YANG model perspective the same data can be
         configured directly within a VLAN sub-interface, or can be
         configured indirectly in a VLAN sub-interface using the
         referenced profile.

         Note that the YANG definition also allows the direct and
         indirect configuration to coexist. In that case the direct
         configuration (within the VLAN sub-interface itself) always
         has priority on the indirect configuration through the data
         nodes in the referenced profile.";
      leaf vsi-profile {
        type leafref {
          path "/bbf-vsi-prof:vsi-profiles"
             + "/bbf-vsi-prof:vsi-profile"
             + "/bbf-vsi-prof:name";
        }
        mandatory true;
        description
          "A reference to a VLAN sub-interface profile.";
      }
    }
  }
}
