module bbf-xpon-onu-activation {
  yang-version 1.1;
  namespace "urn:bbf:yang:bbf-xpon-onu-activation";
  prefix bbf-xpon-onu-activ;

  import ietf-interfaces {
    prefix if;
  }
  import bbf-xpon {
    prefix bbf-xpon;
  }
  import bbf-xpon-onu-activation-common {
    prefix bbf-xpon-onu-activc;
  }
  import bbf-xpon-if-type {
    prefix bbf-xponift;
  }

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on the management of
     Passive Optical Network (PON) interfaces. As such, this module
     is specific to access network equipment (e.g., BBF-specified
     Access Nodes and FTTdp DPUs).

     Specifically, this module defines data nodes and notification
     for controlling the activation of an ONU. One example is to
     give the possibility for the OLT to enable or disable an ONU
     via PLOAM.

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }

  augment "/if:interfaces/if:interface/bbf-xpon:channel-group" {
    when "derived-from-or-self"
       + "(../if:type, 'bbf-xponift:channel-group')";
    description
      "Channel group configuration data to control Optical Network
       Unit (ONU) activation.";
    uses bbf-xpon-onu-activc:onu-controlled-activation-config;
  }

  augment "/if:interfaces-state/if:interface"
        + "/bbf-xpon:channel-group" {
    when "derived-from-or-self"
       + "(../if:type, 'bbf-xponift:channel-group')";
    description
      "Channel group state data associated with the control of
       Optical Network Unit (ONU) activation.";
    uses bbf-xpon-onu-activc:onu-controlled-activation-state {
      refine "onu-controlled-activation-state/onu/serial-number" {
        description
          "An ONU for which activation is explicitly controlled by
           configuration of an entry in the list:
                /if:interfaces/if:interface
                /bbf-xpon:channel-group
                /bbf-xpon-onu-activ:onu-controlled-activation
                /bbf-xpon-onu-activ:onu
           The ONU under activation control is identified by its
           serial number.";
      }
    }
  }

  uses bbf-xpon-onu-activc:inter-channel-group-onu-activation-config;
  uses bbf-xpon-onu-activc:inter-channel-group-onu-activation-state;
}
