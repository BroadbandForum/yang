submodule bbf-vdsl-pointers {
  yang-version 1.1;
  belongs-to bbf-vdsl {
    prefix bbf-vdsl;
  }

  import ietf-interfaces {
    prefix if;
  }
  import bbf-fastdsl {
    prefix bbf-fastdsl;
  }
  import bbf-yang-types {
    prefix bbf-yang;
  }
  include bbf-vdsl-base-body;
  include bbf-vdsl-base;
  include bbf-vdsl-line;
  include bbf-vdsl-service-profiles;
  include bbf-vdsl-spectrum-profiles;
  include bbf-vdsl-quality-profiles;
  include bbf-vdsl-threshold-management;
  include bbf-vdsl-performance-management;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing Vector of Profiles (VoP) on VDSL interfaces.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum-2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef line-config-vector-ref {
    type leafref {
      path "/bbf-vdsl:vdsl/bbf-vdsl:vectors"
         + "/bbf-vdsl:line-config-vector/bbf-vdsl:name";
    }
    description
      "xDSL Line Configuration Vector identifier.";
  }

  typedef threshold-template-ref {
    type leafref {
      path "/bbf-vdsl:vdsl/bbf-vdsl:thresholds/bbf-vdsl:threshold-"
         + "template/bbf-vdsl:name";
    }
    description
      "xDSL Line Threshold Template name.";
  }

  grouping line-config-vector-body {
    description
      "Line Configuration Vector.";
    container channel {
      description
        "Channel profiles. All profile identifiers must be
         configured.";
      leaf downstream-data-rate-profile {
        type bbf-vdsl:downstream-data-rate-profile-ref;
        mandatory true;
        description
          "References a downstream data rate profile to be used to
           configure the line.";
      }
      leaf upstream-data-rate-profile {
        type bbf-vdsl:upstream-data-rate-profile-ref;
        mandatory true;
        description
          "References an upstream data rate profile to be used to
           configure the line.";
      }
      leaf impulse-noise-protection-delay-profile {
        type bbf-vdsl:impulse-noise-protection-delay-profile-ref;
        mandatory true;
        description
          "References an impulse noise protection delay profile to be
           used to configure the line.";
      }
    }
    leaf line-spectrum-profile {
      type bbf-vdsl:line-spectrum-profile-ref;
      mandatory true;
      description
        "References a line spectrum profile to be used to configure
         the line.";
    }
    leaf upstream-power-back-off-profile {
      type bbf-vdsl:upstream-power-back-off-profile-ref;
      mandatory true;
      description
        "References an upstream power back-off profile to be used to
         configure the line.";
    }
    leaf downstream-power-back-off-profile {
      type bbf-vdsl:downstream-power-back-off-profile-ref;
      mandatory true;
      description
        "References a downstream power back-off profile to be used to
         configure the line.";
    }
    leaf radio-frequency-interference-profile {
      type bbf-vdsl:radio-frequency-interference-profile-ref;
      mandatory true;
      description
        "References an radio frequency interference profile to be used
         to configure the line.";
    }
    leaf noise-margin-profile {
      type bbf-vdsl:noise-margin-profile-ref;
      mandatory true;
      description
        "References a noise margin profile to be used to configure the
         line.";
    }
    leaf virtual-noise-profile {
      if-feature "bbf-vdsl:virtual-noise";
      type leafref {
        path "/bbf-vdsl:vdsl/bbf-vdsl:quality/bbf-vdsl:virtual-"
           + "noise-profile/bbf-vdsl:name";
      }
      mandatory true;
      description
        "References a virtual noise profile to be used to configure
         the line.";
    }
    leaf sos-profile {
      if-feature "bbf-vdsl:sos";
      type leafref {
        path "/bbf-vdsl:vdsl/bbf-vdsl:quality/bbf-vdsl:sos-profile/"
           + "bbf-vdsl:name";
      }
      mandatory true;
      description
        "References a Save Our Showtime (SOS) profile to be used to
         configure the line.";
    }
    leaf impulse-noise-monitoring-profile {
      if-feature "bbf-vdsl:impulse-noise-monitoring";
      type leafref {
        path "/bbf-vdsl:vdsl/bbf-vdsl:quality/bbf-vdsl:impulse-"
           + "noise-monitoring-profile/bbf-vdsl:name";
      }
      mandatory true;
      description
        "References an impulse noise monitoring profile to be used to
         configure the line.";
    }
    leaf re-initialization-policy-profile {
      if-feature "bbf-vdsl:re-initialization-policy";
      type leafref {
        path "/bbf-vdsl:vdsl/bbf-vdsl:quality/bbf-vdsl:re-"
           + "initialization-policy-profile/bbf-vdsl:name";
      }
      mandatory true;
      description
        "References a re-initialization policy profile to be used to
         configure the line.";
    }
    leaf vectoring-profile {
      if-feature "bbf-vdsl:vectoring";
      type leafref {
        path "/bbf-vdsl:vdsl/bbf-vdsl:quality/bbf-vdsl:vectoring-"
           + "profile/bbf-vdsl:name";
      }
      mandatory true;
      description
        "References a vectoring profile to be used to configure the
         line.";
    }
    leaf data-gathering-profile {
      if-feature "bbf-vdsl:data-gathering";
      type leafref {
        path "/bbf-vdsl:vdsl/bbf-vdsl:quality/bbf-vdsl:data-"
           + "gathering-profile/bbf-vdsl:name";
      }
      mandatory true;
      description
        "References a data gathering profile to be used to configure
         the line.";
    }
  }

  augment "/bbf-vdsl:vdsl/bbf-vdsl:vectors" {
    description
      "xDSL Line Configuration Vector.";
    list line-config-vector {
      key "name";
      description
        "xDSL Line Configuration Vector.";
      leaf name {
        type bbf-yang:string-ascii64;
        description
          "xDSL Line Configuration Vector Identifier.";
      }
      uses line-config-vector-body;
    }
  }

  augment "/bbf-vdsl:vdsl/bbf-vdsl:thresholds" {
    description
      "xDSL Performance Threshold Management.";
    list threshold-template {
      key "name";
      description
        "xDSL Line Threshold Template.";
      leaf name {
        type bbf-yang:string-ascii64;
        description
          "Template name.";
      }
      grouping threshold-profile {
        description
          "Defines 15 minute and 24 hour line and channel profiles.";
        leaf xtu-15min-line-profile {
          type bbf-vdsl:line-threshold-profile-ref;
          mandatory true;
          description
            "Reference to a line threshold profile for thresholds
             related to 15 minute performance counters.";
        }
        leaf xtu-24hr-line-profile {
          if-feature "bbf-vdsl:performance-24hr";
          type bbf-vdsl:line-threshold-profile-ref;
          mandatory true;
          description
            "Reference to a line threshold profile for thresholds
             related to 24 hour performance counters.";
        }
        leaf xtu-15min-channel-threshold-profile {
          type bbf-vdsl:channel-threshold-profile-ref;
          mandatory true;
          description
            "Reference to a channel threshold profile for thresholds
             related to 15 minute performance counters.";
        }
        leaf xtu-24hr-channel-threshold-profile {
          if-feature "bbf-vdsl:performance-24hr";
          type bbf-vdsl:channel-threshold-profile-ref;
          mandatory true;
          description
            "Reference to a channel threshold profile for thresholds
             related to 24 hour performance counters.";
        }
      }

      container xtu-c {
        description
          "xDSL Tranceiver Unit - Central office (xTU-C) threshold
           profile pointer.";
        uses threshold-profile;
      }
      container xtu-r {
        description
          "xDSL Tranceiver Unit - Remote side (xTU-R) threshold
           profile pointer.";
        uses threshold-profile;
      }
    }
  }

  augment "/if:interfaces/if:interface/bbf-fastdsl:line/bbf-vdsl:"
        + "line" {
    description
      "Augment FastDSL line configuration with VDSL line
       configuration.";
    choice profile-config {
      description
        "The method for configuring profiles used on this VDSL line.
         If no method is configured, the default behavior is
         equivalent to the presence of 'no-profiles-attached'.";
      case no-profiles-attached {
        leaf no-profiles-attached {
          type empty;
          description
            "If present, indicates that no profiles are attached
             to this line.";
        }
      }
      case direct-attachment-mode {
        uses line-config-vector-body;
      }
      case indirect-attachment-mode {
        leaf line-config-vector {
          type bbf-vdsl:line-config-vector-ref;
          description
            "xDSL Line Configuration Vector identifier.
             This identifier must be configured if indirect
             attachment mode is used.";
        }
      }
    }
    leaf threshold-template {
      type bbf-vdsl:threshold-template-ref;
      description
        "xDSL Line Threshold Template identifier. If no threshold
         template is assigned, threshold crossing alert (TCA)
         reporting for all thresholds is disabled.";
    }
  }
}
