module bbf-xpon-statistics-management {
  yang-version 1.1;
  namespace "urn:bbf:yang:bbf-xpon-statistics-management";
  prefix bbf-xpon-sm;

  import ietf-interfaces {
    prefix if;
  }
  import ietf-yang-types {
    prefix yang;
  }
  import bbf-xpon-if-type {
    prefix bbf-xponift;
  }

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on the management of
     Passive Optical Network (PON) interfaces. As such, this module
     is specific to access network equipment (e.g., BBF-specified
     Access Nodes and FTTdp DPUs).

     Specifically, this module augments
     bbf-interfaces-statistics-management to provide xPON-specific
     statistics.

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }

  grouping xpon-phy-sm {
    description
      "xPON PHY statistics.";
    container phy {
      description
        "xPON PHY statistics.";
      leaf corrected-fec-bits {
        type yang:counter64;
        description
          "Count the number of bits that were corrected by the FEC
           function.

           For G-PON, not applicable.
           For XG-PON, not applicable.
           For XGS-PON, not applicable.
           For 25GS-PON, not applicable.
           For NG-PON2, not applicable.
           For 50G-PON, reported per ANI and vANI.";
        reference
          "ITU-T G.9804.2 Table 14-1 - Corrected FEC bits";
      }
      leaf corrected-fec-bytes {
        type yang:counter64;
        description
          "Count the number of bytes that were corrected by the FEC
           function.

           For GPON, reported per ANI and vANI.
           For XG-PON, reported per ANI and vANI.
           For XGS-PON, reported per ANI and vANI.
           For 25GS-PON, reported per ANI and vANI.
           For NG-PON2, reported per ANI and vANI.
           For 50G-PON, not applicable.";
        reference
          "ITU-T G.987.3 Table 14-1 - Corrected FEC bytes;
           ITU-T G.9807.1 Amd.1 Table C.14.1 - Corrected FEC bytes;
           ITU-T G.989.3 Amd.2 Table 14-1 - Corrected FEC bytes";
      }
      leaf corrected-fec-codewords {
        type yang:counter64;
        description
          "Count of Forward Error Correction (FEC) codewords that
           contained errors but were corrected by the FEC function.

           For GPON, reported per ANI and vANI.
           For XG-PON, reported per ANI and vANI.
           For XGS-PON, reported per ANI and vANI.
           For 25GS-PON, reported per ANI and vANI.
           For NG-PON2, reported per ANI and vANI.
           For 50G-PON, reported per ANI and vANI.";
        reference
          "ITU-T G.987.3 Table 14-1 - Corrected FEC codewords;
           ITU-T G.9807.1 Amd.1 Table C.14.1 - Corrected FEC
           codewords;
           ITU-T G.989.3 Amd.2 Table 14-1 - Corrected FEC codewords;
           ITU-T G.9804.2 Table 14-1 - Corrected FEC codewords";
      }
      leaf uncorrectable-fec-codewords {
        type yang:counter64;
        description
          "Count of Forward Error Correction (FEC) codewords that
           contained errors and could not be corrected by the FEC
           function.

           For GPON, reported per ANI, vANI and CT.
           For XG-PON, reported per ANI, vANI and CT.
           For XGS-PON, reported per ANI, vANI and CT.
           For 25GS-PON, reported per ANI, vANI and CT.
           For NG-PON2, reported per ANI, vANI and CT.
           For 50G-PON, reported per ANI, vANI and CT.";
        reference
          "ITU-T G.987.3 Table 14-1 - Uncorrectable FEC codewords;
           ITU-T G.9807.1 Amd.1 Table C.14.1 - Uncorrectable FEC
           codewords;
           ITU-T G.989.3 Amd.2 Table 14-1 - Uncorrectable FEC
           codewords;
           ITU-T G.9804.2 Table 14-1 - Uncorrectable FEC codewords";
      }
      leaf in-fec-codewords {
        type yang:counter64;
        description
          "Count of total received Forward Error Correction (FEC)
           codewords.

           For GPON, reported per ANI, vANI and CT.
           For XG-PON, reported per ANI, vANI and CT.
           For XGS-PON, reported per ANI, vANI and CT.
           For 25GS-PON, reported per ANI, vANI and CT.
           For NG-PON2, reported per ANI, vANI and CT.
           For 50G-PON, reported per ANI, vANI and CT.";
        reference
          "ITU-T G.987.3 Table 14-1 - Total FEC codewords;
           ITU-T G.9807.1 Amd.1 Table C.14.1 - Total FEC codewords;
           ITU-T G.989.3 Amd.2 Table 14-1 - Total FEC codewords;
           ITU-T G.9804.2 Table 14-1 - Total FEC codewords";
      }
    }
  }

  augment "/if:interfaces-state/if:interface/if:statistics" {
    when
      " derived-from-or-self(../if:type, 'bbf-xponift:ani') or "
    + " derived-from-or-self(../if:type, 'bbf-xponift:v-ani') or "
    + " derived-from-or-self(../if:type, "
    + "'bbf-xponift:channel-termination')" {
      description
        "Only applicable to Access Network Interfaces (ANI), virtual
         Access Network Interfaces (vANI) or Channel Termination (CT)
         interfaces.";
    }
    description
      "Augment the interface statistics with xPON-specific counters.";
    container xpon {
      description
        "xPON interface statistics.";
      uses xpon-phy-sm;
    }
  }
}
