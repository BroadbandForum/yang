submodule bbf-melt-pmd-reporting-parameter-body {
  yang-version 1.1;
  belongs-to bbf-melt {
    prefix bbf-melt;
  }

  include bbf-melt-pmd-measurement-parameter-body;
  include bbf-melt-base;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     Metallic Line Test Physical Medium Dependent (MELT-PMD) reporting
     parameters.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef melt-pmd-reporting-parameter {
    type enumeration {
      enum measurement-frequency {
        description
          "This parameter is the measurement frequency for a
           3-element capacitance measurement, if performed with a
           sinewave signal, or a for 3-element complex admittance
           measurement. The range of valid values is from 10 to 1000
           Hz with a granularity of 1 Hz.";
        reference
          "ITU-T G.996.2 clause E.2.2.1 (MELT-MFREQ)";
      }
      enum foreign-voltage-input-impedance {
        description
          "This parameter reports the nominal input impedance of the
           measuring instrument during foreign voltage tests. The
           range of valid values is from 0 to 10 megaohms with a
           granularity of 1 ohm.";
        reference
          "ITU-T G.996.2 clause E.2.2.2 (MELT-IMP-V)";
      }
      enum loop-complex-admittance-measurement-voltage {
        description
          "This parameter is the peak amplitude of the differential
           sinewave used by the measurement of the loop complex
           admittance with a high voltage metallic test. The range of
           valid values is from 0 to 150 volts and it shall be
           represented in linear format with a granularity of 0.1
           volts.";
        reference
          "ITU-T G.996.2 clauses E.1.1.7 and E.2.2.3 (MELT-HCA-V)";
      }
    }
    description
      "An enumerated list of MELT PMD reporting parameters.";
  }

  grouping pmd-reporting-parameters {
    description
      "Defines the Metallic Line Test Physical Medium Dependent
       (MELT-PMD) reporting parameters.";
    leaf measurement-frequency {
      type uint16 {
        range "10..1000";
      }
      units "Hz";
      description
        "This parameter is the measurement frequency for a 3-element
         capacitance measurement, if performed with a sinewave
         signal, or a for 3-element complex admittance measurement.
         The range of valid values is from 10 to 1000 Hz with a
         granularity of 1 Hz.";
      reference
        "ITU-T G.996.2 clause E.2.2.1 (MELT-MFREQ)";
    }
    leaf foreign-voltage-input-impedance {
      type uint32 {
        range "0..10000000";
      }
      units "ohms";
      description
        "This parameter reports the nominal input impedance of the
         measuring instrument during foreign voltage tests. The range
         of valid values is from 0 to 10 megaohms with a granularity
         of 1 ohm.";
      reference
        "ITU-T G.996.2 clause E.2.2.2 (MELT-IMP-V)";
    }
    leaf loop-complex-admittance-measurement-voltage {
      type measurement-voltage;
      description
        "This parameter is the peak amplitude of the differential
         sinewave used by the measurement of the loop complex
         admittance with a high voltage metallic test. The range of
         valid values is from 0 to 150 volts and it shall be
         represented in linear format with a granularity of 0.1
         volts.";
      reference
        "ITU-T G.996.2 clauses E.1.1.7 and E.2.2.3 (MELT-HCA-V)";
    }
    leaf unreliability-indicator {
      if-feature "bbf-melt:melt-pmd-reporting-parameter-reliability";
      type bits {
        bit measurement-frequency {
          description
            "This parameter is the measurement frequency for a
             3-element capacitance measurement, if performed with a
             sinewave signal, or a for 3-element complex admittance
             measurement. The range of valid values is from 10 to 1000
             Hz with a granularity of 1 Hz.";
          reference
            "ITU-T G.996.2 clause E.2.2.1 (MELT-MFREQ)";
        }
        bit foreign-voltage-input-impedance {
          description
            "This parameter reports the nominal input impedance of the
             measuring instrument during foreign voltage tests. The
             range of valid values is from 0 to 10 megaohms with a
             granularity of 1 ohm.";
          reference
            "ITU-T G.996.2 clause E.2.2.2 (MELT-IMP-V)";
        }
        bit loop-complex-admittance-measurement-voltage {
          description
            "This parameter is the peak amplitude of the differential
             sinewave used by the measurement of the loop complex
             admittance with a high voltage metallic test. The range
             of valid values is from 0 to 150 volts and it shall be
             represented in linear format with a granularity of 0.1
             volts.";
          reference
            "ITU-T G.996.2 clauses E.1.1.7 and E.2.2.3 (MELT-HCA-V)";
        }
      }
      description
        "The unreliability indicator provides the set of parameters
         whose data can be considered to be unreliable.

         Possible reasons that the data is unreliable:
           - The measurement may not have been able to run, possibly
             due to external conditions.
           - The result is not reliable as the accuracy may be
             degraded due to external conditions.";
      reference
        "ITU-T G.996.2 clause E.2.2.4 (Reliability indicator)";
    }
    container melt-pmd-reporting-vendor-specific-status {
      if-feature "bbf-melt:melt-pmd-reporting-parameter-reliability";
      description
        "Vendor specific status associated with each MELT
         reporting test.";
      list status {
        key "parameter";
        description
          "A list of per parameter test status.";
        leaf parameter {
          type melt-pmd-reporting-parameter;
          description
            "The MELT PMD reporting parameter.";
        }
        leaf message {
          type string;
          description
            "Vendor specific status message for each of the
             MELT PMD reporting parameters.";
        }
      }
    }
  }
}
