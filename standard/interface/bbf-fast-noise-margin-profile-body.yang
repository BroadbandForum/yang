submodule bbf-fast-noise-margin-profile-body {
  yang-version 1.1;
  belongs-to bbf-fast {
    prefix bbf-fast;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing noise margin profiles.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping seamless-rate-adaptation-parameters {
    description
      "Seamless Rate Adaptation (SRA) configuration parameters
       applicable to both upstream and downstream.";
    reference
      "ITU-T G.997.2 clause 7.1.4";
    leaf upshift-noise-margin {
      type uint16 {
        range "0..310" {
          description
            "Defines a range from 0.0 to 31.0 dB.";
        }
      }
      units "0.1 dB";
      default "70";
      description
        "If the noise margin (SNRM) is above the upshift noise
         margin and stays above that for more than the time specified
         by the minimum upshift rate adaptation interval (SRA-UTIME),
         the transmitting FAST Transceiver Unit (FTU) autonomously
         attempts to increase the net data rate (NDR).";
      reference
        "ITU-T G.997.2 clauses 7.1.4.1 (SRA-USNRMds) and 7.1.4.2
         (SRA-USNRMus);
         ITU-T G.9701 clause 12.3.4.2.1";
    }
    leaf upshift-noise-margin-in-l2.1 {
      type uint16 {
        range "0..310" {
          description
            "Defines a range from 0.0 to 31.0 dB.";
        }
      }
      units "0.1 dB";
      default "70";
      description
        "If the noise margin in the L2.1N and L2.1B link states
         (L2.1-SNRM) is above the upshift noise margin and stays
         above that for more than the time specified by the minimum
         upshift rate adaptation interval (SRA-UTIME), the FAST
         Transceiver Unit - Remote side (FTU-R) autonomously attempts
         to increase the net data rate in the L2.1 link state.";
      reference
        "ITU-T G.997.2 clauses 7.1.10.4 (L2.1-SRA-USNRMds) and
         7.1.10.5 (L2.1-SRA-USNRMus);
         ITU-T G.9701 clause 13.4.1.4.7";
    }
    leaf minimum-time-interval-upshift-sra {
      type uint16 {
        range "0..16383";
      }
      units "seconds";
      default "8";
      description
        "Defines the interval of time the noise margin (SNRM) should
         stay above the upshift noise margin (SRA-USNRM) before the
         transmitting FAST Transceiver Unit (FTU) autonomously
         attempts to increase the net data rate (NDR).";
      reference
        "ITU-T G.997.2 clauses 7.1.4.3 (SRA-UTIMEds) and 7.1.4.4
         (SRA-UTIMEus);
         ITU-T G.9701 clause 12.3.4.2.1";
    }
    leaf downshift-noise-margin-in-l2.1 {
      type uint16 {
        range "0..310" {
          description
            "Defines a range from 0.0 to 31.0 dB.";
        }
      }
      units "0.1 dB";
      default "50";
      description
        "If the noise margin in the L2.1N and L2.1B link states
         (L2.1-SNRM) is below the downshift noise margin and stays
         below that for more than the time specified by the minimum
         downshift rate adaptation interval (SRA-DTIME), the FAST
         Transceiver Unit - Remote side (FTU-R) autonomously attempts
         to decrease the net data rate in the L2.1 link state.";
      reference
        "ITU-T G.997.2 clauses 7.1.10.6 (L2.1-SRA-DSNRMds) and
         7.1.10.7 (L2.1-SRA-DSNRMus);
         ITU-T G.9701 clause 13.4.1.4.7";
    }
    leaf minimum-time-interval-downshift-sra {
      type uint16 {
        range "0..16383";
      }
      units "seconds";
      default "2";
      description
        "Defines the interval of time the noise margin (SNRM) should
         stay below the downshift noise margin (SRA-DSNRM) before the
         transmitting FAST Transceiver Unit (FTU) autonomously
         attempts to decrease the net data rate (NDR).";
      reference
        "ITU-T G.997.2 clauses 7.1.4.7 (SRA-DTIMEds) and 7.1.4.8
         (SRA-DTIMEus);
         ITU-T G.9701 clause 12.3.4.2.1";
    }
  }

  grouping robust-management-channel-parameters {
    description
      "Robust Management Channel (RMC) configuration parameters
       applicable to both upstream and downstream.";
    reference
      "ITU-T G.997.2 clause 7.1.6";
    leaf target-noise-margin {
      type uint16 {
        range "0..310" {
          description
            "Defines a range from 0.0 to 31.0 dB.";
        }
      }
      units "0.1 dB";
      default "60";
      description
        "Defines the Robust Management Channel (RMC) noise margin
         (SNRMRMC) that the FAST Transceiver Unit (FTU) receiver
         shall achieve, relative to the Bit Error Rate (BER)
         requirement, or better, to successfully complete
         initialization.";
      reference
        "ITU-T G.997.2 clauses 7.1.6.1 (TARSNRM-RMCds) and 7.1.6.2
         (TARSNRM-RMCus);
         ITU-T G.9701 clause 12.3.3.2.1";
    }
    leaf minimum-noise-margin {
      type uint16 {
        range "0..310" {
          description
            "Defines a range from 0.0 to 31.0 dB.";
        }
      }
      units "0.1 dB";
      must '. <= ../target-noise-margin' {
        error-message "'minimum-noise-margin' is greater than the "
                    + "'target-noise-margin'.";
        description
          "The minimum noise margin must be less than or equal to
           the target noise margin.";
      }
      default "0";
      description
        "Defines the minimum noise margin the FAST Transceiver Unit
         (FTU) receiver tolerates for the Robust Management Channel
         (RMC). If the RMC noise margin (SNRM-RMC) falls below
         this level, the FTU receiver initiates the RMC Parameter
         Adjustment (RPA) procedure.";
      reference
        "ITU-T G.997.2 clauses 7.1.6.3 (MINSNRM-RMCds) and 7.1.6.4
         (MINSNRM-RMCus);
         ITU-T G.9701 clause 13.2.1.3";
    }
    leaf maximum-bit-loading {
      type uint8 {
        range "2..6";
      }
      default "6";
      description
        "Defines the maximum allowed bit-loading for the Robust
         Management Channel (RMC) sub-carriers.";
      reference
        "ITU-T G.997.2 clauses 7.1.6.5 (MAXBL-RMCds) and 7.1.6.6
         (MAXBL-RMCus);
         ITU-T G.9701 clause 12.3.3.2.1";
    }
  }

  grouping noise-margin-profile {
    description
      "Defines the contents of a Noise Margin Profile.";
    container downstream {
      description
        "Downstream noise margin profile.";
      container noise-margin {
        description
          "Noise margin parameters.";
        leaf target-noise-margin {
          type uint16 {
            range "0..310" {
              description
                "Defines a range from 0.0 to 31.0 dB.";
            }
          }
          units "0.1 dB";
          must ". <= ../../seamless-rate-adaptation/
                                         upshift-noise-margin" {
            error-message
              "The downstream 'target-noise-margin' is greater than "
            + "the 'upshift-noise-margin'.";
            description
              "The target noise margin must be less than or equal to
               the upshift noise margin.";
          }
          default "60";
          description
            "Defines the target noise margin for the Channel
             Initialization Policy.";
          reference
            "ITU-T G.997.2 clause 7.1.3.1 (TARSNRMds);
             ITU-T G.9701 clause 12.3.7";
        }
        leaf minimum-noise-margin {
          type uint16 {
            range "0..310" {
              description
                "Defines a range from 0.0 to 31.0 dB.";
            }
          }
          units "0.1 dB";
          must ". <= ../../seamless-rate-adaptation/
                                         downshift-noise-margin" {
            error-message
              "The downstream 'minimum-noise-margin' is greater than "
            + "the 'downshift-noise-margin'.";
            description
              "The minimum noise margin must be less than or equal to
               the downshift noise margin.";
          }
          default "0";
          description
            "Defines the minimum noise margin the FAST Transceiver
             Unit (FTU) receiver shall tolerate. If the noise margin
             (SNRM) falls below this level, the FTU receiver requests
             the FTU transmitter to increase the FTU transmit power.
             If an increase to FTU transmit power is not possible, a
             loss-of-margin(lom) defect occurs. Upon persistency of
             the lom defect, the FTU receiver triggers a
             re-initialization.";
          reference
            "ITU-T G.997.2 clause 7.1.3.4 (MINSNRMds);
             ITU-T G.9701 clauses 12.1.4.2 and 12.3.4.2.1";
        }
        leaf target-noise-margin-in-l2 {
          type uint16 {
            range "0..310" {
              description
                "Defines a range from 0.0 to 31.0 dB.";
            }
          }
          units "0.1 dB";
          must '. >= ../minimum-noise-margin' {
            error-message
              "The downstream 'target-noise-margin-in-l2' is less "
            + "than the 'minimum-noise-margin'.";
            description
              "The target low power noise margin must be greater than
               or equal to the minimum noise margin.";
          }
          default "60";
          description
            "Defines the target noise margin used during the L2.1 and
             L2.2 link state for both the upstream and downstream
             direction.";
          reference
            "ITU-T G.997.2 clause 7.1.10.1 (L2-TARSNRM);
             ITU-T G.9701 clauses 13.4.1.4 and 13.4.2.4";
        }
        leaf maximum-noise-margin-in-l2.1 {
          type uint16 {
            range "0..310 | 511" {
              description
                "Defines a range from 0.0 to 31.0 dB.
                 Special value 511: No maximum bound.";
            }
          }
          units "0.1 dB";
          must '. >= ../target-noise-margin-in-l2' {
            error-message
              "The downstream 'maximum-noise-margin-in-l2.1' is less "
            + "than the 'target-noise-margin-in-l2'.";
            description
              "The maximum low power noise margin must be greater than
               or equal to the target low power noise margin.";
          }
          default "511";
          description
            "Defines the maximum noise margin allowed during the L2.1
             and L2.2 link state for both the upstream and downstream
             direction. The special value, 511, indicates there is no
             maximum bound for the noise margin (i.e., the maximum
             noise margin is infinite).";
          reference
            "ITU-T G.997.2 clause 7.1.10.2 (L2-MAXSNRM);
             ITU-T G.9701 clauses 13.4.1.4 and 13.4.2.4";
        }
      }
      container seamless-rate-adaptation {
        description
          "Seamless Rate Adaptation(SRA) parameters.";
        leaf downshift-noise-margin {
          type uint16 {
            range "0..310" {
              description
                "Defines a range from 0.0 to 31.0 dB.";
            }
          }
          units "0.1 dB";
          must '. <= ../../noise-margin/target-noise-margin' {
            error-message
              "The downstream 'downshift-noise-margin' is greater "
            + "than the 'target-noise-margin'.";
            description
              "The downshift noise margin must be less than or equal
               to the target noise margin.";
          }
          default "50";
          description
            "If the noise margin (SNRM) is below the downshift noise
             margin and stays below that for more than the time
             specified by the minimum downshift rate adaptation
             interval (SRA-DTIME), the transmitting FAST Transceiver
             Unit (FTU) autonomously attempts to decrease the net data
             rate (NDR).";
          reference
            "ITU-T G.997.2 clause 7.1.4.5 (SRA-DSNRMds);
             ITU-T G.9701 clause 12.3.4.2.1";
        }
        uses seamless-rate-adaptation-parameters;
      }
      container robust-management-channel {
        description
          "Robust Management Channel (RMC) parameters.";
        uses robust-management-channel-parameters;
      }
    }
    container upstream {
      description
        "Upstream noise margin profile.";
      container noise-margin {
        description
          "Noise margin parameters.";
        leaf target-noise-margin {
          type uint16 {
            range "0..310" {
              description
                "Defines a range from 0.0 to 31.0 dB.";
            }
          }
          units "0.1 dB";
          must ". <= ../../seamless-rate-adaptation/
                                         upshift-noise-margin" {
            error-message
              "The upstream 'target-noise-margin' is greater than "
            + "the 'upshift-noise-margin'.";
            description
              "The target noise margin must be less than or equal to
               the upshift noise margin.";
          }
          default "60";
          description
            "Defines the target noise margin for the Channel
             Initialization Policy.";
          reference
            "ITU-T G.997.2 clause 7.1.3.2 (TARSNRMus);
             ITU-T G.9701 clause 12.3.7";
        }
        leaf minimum-noise-margin {
          type uint16 {
            range "0..310" {
              description
                "Defines a range from 0.0 to 31.0 dB.";
            }
          }
          units "0.1 dB";
          must ". <= ../../seamless-rate-adaptation/
                                         downshift-noise-margin" {
            error-message
              "The upstream 'minimum-noise-margin' is greater than "
            + "the 'downshift-noise-margin'.";
            description
              "The minimum noise margin must be less than or equal to
               the downshift noise margin.";
          }
          default "0";
          description
            "Defines the minimum noise margin the FAST Transceiver
             Unit (FTU) receiver shall tolerate. If the noise margin
             (SNRM) falls below this level, the FTU receiver requests
             the FTU transmitter to increase the FTU transmit power.
             If an increase to FTU transmit power is not possible, a
             loss-of-margin(lom) defect occurs. Upon persistency of
             the lom defect, the FTU receiver triggers a
             re-initialization.";
          reference
            "ITU-T G.997.2 clause 7.1.3.5 (MINSNRMus);
             ITU-T G.9701 clauses 12.1.4.2 and 12.3.4.2.1";
        }
        leaf maximum-noise-margin {
          type uint16 {
            range "0..310 | 511" {
              description
                "Defines a range from 0.0 to 31.0 dB.
                 Special value 511: No maximum bound.";
            }
          }
          units "0.1 dB";
          must ". >= ../../seamless-rate-adaptation/
                                         upshift-noise-margin" {
            error-message
              "The upstream 'maximum-noise-margin' is less than the "
            + "'upshift-noise-margin'.";
            description
              "The maximum noise margin must be greater than or equal
               to the upshift noise margin.";
          }
          default "511";
          description
            "Defines the maximum noise margin used in the Channel
             Initialization Policy.
             A special value, 511, indicates there is no maximum bound
             for the noise margin (i.e., the maximum noise margin is
             infinite).";
          reference
            "ITU-T G.997.2 clause 7.1.3.3 (MAXSNRMus);
             ITU-T G.9701 clause 12.3.7";
        }
        leaf target-noise-margin-in-l2 {
          type uint16 {
            range "0..310" {
              description
                "Defines a range from 0.0 to 31.0 dB.";
            }
          }
          units "0.1 dB";
          must '. >= ../minimum-noise-margin' {
            error-message
              "The upstream 'target-noise-margin-in-l2' is less than "
            + "the 'minimum-noise-margin'.";
            description
              "The target low power noise margin must be greater than
               or equal to the minimum noise margin.";
          }
          default "60";
          description
            "Defines the target noise margin used during the L2.1 and
             L2.2 link state for both the upstream and downstream
             direction.";
          reference
            "ITU-T G.997.2 clause 7.1.10.1 (L2-TARSNRM);
             ITU-T G.9701 clauses 13.4.1.4 and 13.4.2.4";
        }
        leaf maximum-noise-margin-in-l2.1 {
          type uint16 {
            range "0..310 | 511" {
              description
                "Defines a range from 0.0 to 31.0 dB.";
            }
          }
          units "0.1 dB";
          must '. >= ../target-noise-margin-in-l2' {
            error-message
              "The upstream 'maximum-noise-margin-in-l2.1' is less "
            + "than the 'target-noise-margin-in-l2'.";
            description
              "The maximum low power noise margin must be greater than
               or equal to the target low power noise margin.";
          }
          default "511";
          description
            "Defines the maximum noise margin allowed during the L2.1
             and L2.2 link state for both the upstream and downstream
             direction. The special value, 511, indicates there is no
             maximum bound for the noise margin (i.e., the maximum
             noise margin is infinite).";
          reference
            "ITU-T G.997.2 clause 7.1.10.2 (L2-MAXSNRM);
             ITU-T G.9701 clauses 13.4.1.4 and 13.4.2.4";
        }
      }
      container seamless-rate-adaptation {
        description
          "Seamless Rate Adaptation(SRA) parameters.";
        leaf downshift-noise-margin {
          type uint16 {
            range "0..310" {
              description
                "Defines a range from 0.0 to 31.0 dB.";
            }
          }
          units "0.1 dB";
          must '. <= ../../noise-margin/target-noise-margin' {
            error-message
              "The upstream 'downshift-noise-margin' is greater than "
            + "the 'target-noise-margin'.";
            description
              "The downshift noise margin must be less than or equal
               to the target noise margin.";
          }
          default "50";
          description
            "If the noise margin (SNRM) is below the downshift noise
             margin and stays below that for more than the time
             specified by the minimum downshift rate adaptation
             interval (SRA-DTIME), the transmitting FAST Transceiver
             Unit (FTU) autonomously attempts to decrease the net data
             rate (NDR).";
          reference
            "ITU-T G.997.2 clause 7.1.4.6 (SRA-DSNRMus);
             ITU-T G.9701 clause 12.3.4.2.1";
        }
        uses seamless-rate-adaptation-parameters;
      }
      container robust-management-channel {
        description
          "Robust Management Channel (RMC) parameters.";
        uses robust-management-channel-parameters;
      }
    }
  }
}
