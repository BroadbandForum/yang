submodule bbf-melt-processing-derived-parameter-body {
  yang-version 1.1;
  belongs-to bbf-melt {
    prefix bbf-melt;
  }

  include bbf-melt-base;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     Metallic Line Test Processing (MELT-P) derived parameters.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef melt-processing-derived-parameter {
    type enumeration {
      enum open-wire-failure-type {
        description
          "This sub-parameter is a five state indication of the type
           of open wire failure defined as follows:

           1) No open wire failure detected
           2) Tip and ring wires open in equal distance
           3) Tip wire open
           4) Ring wire open
           5) Undefined.

           NOTE - An error-free loop will be classified as failure
           state 2) in case that the remote end of the loop was left
           open during the measurement, or the connected Customer
           Premises Equipment (CPE) could not be detected (too low
           parallel CPE system capacitance).";
        reference
          "ITU-T G.996.2 clause F.2.2.1.1 (MELT-O-WIRE-type)";
      }
      enum open-wire-failure-distance {
        description
          "This parameter represents a best-effort estimate of the
           distance of the detected open wire failure from the
           measurement point, i.e., from the central office or of
           the total loop length if no failure is detected. A priori
           knowledge of the loop characteristics is required for
           reliable estimation of the distance. The range of valid
           values is from 0 to 10000 meters with a granularity of 1
           meter.";
        reference
          "ITU-T G.996.2 clauses F.2.1.2 and F.2.2.1.2
           (MELT-O-WIRE-DIST)";
      }
      enum short-circuit-failure-type {
        description
          "This parameter is a six-state indication of the type of
           short circuit failure defined as follows:

           1) No short circuit detected
           2) Tip and ring wires shorted to GND
           3) Tip wire shorted to GND
           4) Ring wire shorted to GND
           5) Tip and ring wires shorted to each other
           6) Undefined.";
        reference
          "ITU-T G.996.2 clause F.2.2.2.1 (MELT-S-CCT-type)";
      }
      enum leakage-identification {
        description
          "This parameter indicates a leakage to GND failure,
           classified into the following states:

           1) No leakage detected
           2) Tip and ring wire leaking to GND
           3) Tip wire leaking to GND
           4) Ring wire leaking to GND.";
        reference
          "ITU-T G.996.2 clause F.2.2.3 (MELT-LEAK-ID)";
      }
      enum resistive-fault-identification {
        description
          "This parameter indicates a resistive fault to GND
           failure, classified into the following states:

           1) No resistive fault detected
           2) Resistive fault tip and ring to GND
           3) Resistive fault tip to GND
           4) Resistive fault ring to GND.";
        reference
          "ITU-T G.996.2 clause F.2.2.4 (MELT-RFAULT-ID)";
      }
      enum foreign-voltage-type-classification {
        description
          "The foreign voltage impairment in the loop under test is
           classified into the following states:

           1) No foreign voltage detected
           2) 16 2/3 Hz AC voltage
           3) 25 Hz AC voltage
           4) 50 Hz AC voltage
           5) 60 Hz AC voltage
           6) POTS equipment (-48 volts DC)
           7) ISDN equipment (-96 volts DC)
           8) Undefined foreign voltage detected.

           This classification shall be done separately for both,
           the tip and the ring wire.";
        reference
          "ITU-T G.996.2 clause F.2.2.5.1 (MELT-FV-TYPE)";
      }
      enum foreign-voltage-level-classification {
        description
          "This parameter provides a general classification of the
           foreign voltage into the following classes:

           1) hazardous potential (e.g., power contact)
           2) foreign electromotive force
           3) other.";
        reference
          "ITU-T G.996.2 clause F.2.2.5.2 (MELT-FV-LEVEL)";
      }
      enum far-end-signature-topology-type-identification {
        description
          "This parameter specifies the topology types of the
           detected far-end signature.

           Valid response values are:

           - no signature detected
           - unknown signature
           - signature type DR detected
           - signature type ZRC detected.";
        reference
          "ITU-T G.996.2 clause F.2.2.6.1 (MELT-FES-ID)";
      }
      enum cpe-identification-capacitive {
        description
          "Customer Premises Equipment (CPE) detected shall be
           reported if the measured capacitance value CTR-Term is
           >= MELT-SYSC-CPE. CTR-Term shall represent the termination
           capacitance only. Therefore, the line capacitance shall be
           subtracted from the measured CTR value. For this equation
           to hold, the MELT-SYSC-CPE value should be derived from the
           nominal CPE capacitance by accounting for all tolerances
           and be set to the minimum possible measurement result.";
        reference
          "ITU-T G.996.2 clause F.2.2.7 (MELT-CPE-ID)";
      }
    }
    description
      "An enumerated list of MELT processing derived parameters.";
  }

  grouping processing-derived-parameters {
    description
      "Defines the Metallic Line Test Processing (MELT-P) derived
       parameters.";
    leaf open-wire-failure-type {
      type enumeration {
        enum no-open {
          description
            "No open wire failure detected.";
        }
        enum tip-ring-open {
          description
            "Tip and ring wires open in equal distance.";
        }
        enum tip-open {
          description
            "Tip wire open.";
        }
        enum ring-open {
          description
            "Ring wire open.";
        }
        enum undefined {
          description
            "Undefined.";
        }
      }
      description
        "This sub-parameter is a five state indication of the type of
         open wire failure defined as follows:

         1) No open wire failure detected
         2) Tip and ring wires open in equal distance
         3) Tip wire open
         4) Ring wire open
         5) Undefined.

         NOTE - An error-free loop will be classified as failure
         state 2) in case that the remote end of the loop was left
         open during the measurement, or the connected Customer
         Premises Equipment (CPE) could not be detected (too low
         parallel CPE system capacitance).";
      reference
        "ITU-T G.996.2 clause F.2.2.1.1 (MELT-O-WIRE-type)";
    }
    leaf open-wire-failure-distance {
      type uint16 {
        range "0..10000";
      }
      units "meters";
      description
        "This parameter represents a best-effort estimate of the
         distance of the detected open wire failure from the
         measurement point, i.e., from the central office or of the
         total loop length if no failure is detected. A priori
         knowledge of the loop characteristics is required for
         reliable estimation of the distance. The range of valid
         values is from 0 to 10000 meters with a granularity of 1
         meter.";
      reference
        "ITU-T G.996.2 clauses F.2.1.2 and F.2.2.1.2
         (MELT-O-WIRE-DIST)";
    }
    leaf short-circuit-failure-type {
      type enumeration {
        enum no-short {
          description
            "No short circuit detected.";
        }
        enum tip-ring-short-to-ground {
          description
            "Tip and ring wires shorted to ground (GND).";
        }
        enum tip-short-to-ground {
          description
            "Tip wire shorted to ground (GND).";
        }
        enum ring-short-to-ground {
          description
            "Ring wire shorted to ground (GND).";
        }
        enum tip-ring-short-to-each-other {
          description
            "Tip and ring wires shorted to each other.";
        }
        enum undefined {
          description
            "Undefined.";
        }
      }
      description
        "This parameter is a six-state indication of the type of
         short circuit failure defined as follows:

         1) No short circuit detected
         2) Tip and ring wires shorted to GND
         3) Tip wire shorted to GND
         4) Ring wire shorted to GND
         5) Tip and ring wires shorted to each other
         6) Undefined.";
      reference
        "ITU-T G.996.2 clause F.2.2.2.1 (MELT-S-CCT-type)";
    }
    leaf leakage-identification {
      type enumeration {
        enum no-leakage {
          description
            "No leakage detected.";
        }
        enum tip-ring-leaking {
          description
            "Tip and ring wire leaking to ground (GND).";
        }
        enum tip-leaking {
          description
            "Tip wire leaking to ground (GND).";
        }
        enum ring-leaking {
          description
            "Ring wire leaking to ground (GND).";
        }
      }
      description
        "This parameter indicates a leakage to ground (GND) failure,
         classified into the following states:

         1) No leakage detected
         2) Tip and ring wire leaking to GND
         3) Tip wire leaking to GND
         4) Ring wire leaking to GND.";
      reference
        "ITU-T G.996.2 clause F.2.2.3 (MELT-LEAK-ID)";
    }
    leaf resistive-fault-identification {
      type enumeration {
        enum no-fault {
          description
            "No resistive fault detected.";
        }
        enum tip-ring-fault {
          description
            "Resistive fault tip and ring to ground (GND).";
        }
        enum tip-fault {
          description
            "Resistive fault tip to ground (GND).";
        }
        enum ring-fault {
          description
            "Resistive fault ring to ground (GND).";
        }
      }
      description
        "This parameter indicates a resistive fault to ground (GND)
         failure, classified into the following states:

         1) No resistive fault detected
         2) Resistive fault tip and ring to GND
         3) Resistive fault tip to GND
         4) Resistive fault ring to GND.";
      reference
        "ITU-T G.996.2 clause F.2.2.4 (MELT-RFAULT-ID)";
    }
    leaf foreign-voltage-type-classification {
      type enumeration {
        enum no-foreign-voltage-detected {
          description
            "No foreign voltage detected.";
        }
        enum 16-hz-ac-voltage {
          description
            "16 2/3 Hz AC voltage on both tip and ring wires.";
        }
        enum 25-hz-ac-voltage {
          description
            "25 Hz AC voltage on both tip and ring wires.";
        }
        enum 50-hz-ac-voltage {
          description
            "50 Hz AC voltage on both tip and ring wires.";
        }
        enum 60-hz-ac-voltage {
          description
            "60 Hz AC voltage on both tip and ring wires.";
        }
        enum pots-equipment {
          description
            "POTS equipment (-48 volts DC) on both tip and ring
             wires.";
        }
        enum isdn-equipment {
          description
            "ISDN equipment (-96 volts DC) on both tip and ring
             wires.";
        }
        enum undefined-foreign-voltage-detected {
          description
            "Undefined foreign voltage detected on both tip and
             ring wires.";
        }
        enum 16-hz-ac-voltage-tip {
          description
            "16 2/3 Hz AC voltage on the tip wire.";
        }
        enum 16-hz-ac-voltage-ring {
          description
            "16 2/3 Hz AC voltage on the ring wire.";
        }
        enum 25-hz-ac-voltage-tip {
          description
            "25 Hz AC voltage on the the tip wire.";
        }
        enum 25-hz-ac-voltage-ring {
          description
            "25 Hz AC voltage on the the ring wire.";
        }
        enum 50-hz-ac-voltage-tip {
          description
            "50 Hz AC voltage on the tip wire.";
        }
        enum 50-hz-ac-voltage-ring {
          description
            "50 Hz AC voltage on the ring wire.";
        }
        enum 60-hz-ac-voltage-tip {
          description
            "60 Hz AC voltage on the tip wire.";
        }
        enum 60-hz-ac-voltage-ring {
          description
            "60 Hz AC voltage on the ring wire.";
        }
        enum pots-equipment-tip {
          description
            "POTS equipment (-48 volts DC) on the tip wire.";
        }
        enum pots-equipment-ring {
          description
            "POTS equipment (-48 volts DC) on the ring wire.";
        }
        enum isdn-equipment-tip {
          description
            "ISDN equipment (-96 volts DC) on the tip wire.";
        }
        enum isdn-equipment-ring {
          description
            "ISDN equipment (-96 volts DC) on the ring wire.";
        }
        enum undefined-foreign-voltage-detected-tip {
          description
            "Undefined foreign voltage detected on the tip wire.";
        }
        enum undefined-foreign-voltage-detected-ring {
          description
            "Undefined foreign voltage detected on the ring wire.";
        }
      }
      description
        "The foreign voltage impairment in the loop under test is
         classified into the following states:

         1) No foreign voltage detected
         2) 16 2/3 Hz AC voltage
         3) 25 Hz AC voltage
         4) 50 Hz AC voltage
         5) 60 Hz AC voltage
         6) POTS equipment (-48 volts DC)
         7) ISDN equipment (-96 volts DC)
         8) Undefined foreign voltage detected.

         This classification shall be done separately for both, the
         tip and the ring wire.";
      reference
        "ITU-T G.996.2 clause F.2.2.5.1 (MELT-FV-TYPE)";
    }
    leaf foreign-voltage-level-classification {
      type enumeration {
        enum hazardous-potential {
          description
            "Hazardous potential (e.g., power contact).";
        }
        enum foreign-electromotive-force {
          description
            "Foreign electromotive force.";
        }
        enum other {
          description
            "Other.";
        }
      }
      description
        "This parameter provides a general classification of the
         foreign voltage into the following classes:

         1) hazardous potential (e.g., power contact)
         2) foreign electromotive force
         3) other.";
      reference
        "ITU-T G.996.2 clause F.2.2.5.2 (MELT-FV-LEVEL)";
    }
    leaf far-end-signature-topology-type-identification {
      type enumeration {
        enum no-signature-detected {
          description
            "No signature detected.";
        }
        enum unknown-signature {
          description
            "Unknown signature.";
        }
        enum signature-type-dr {
          description
            "Signature type DR detected.";
        }
        enum signature-type-zrc {
          description
            "Signature type ZRC detected.";
        }
        enum signature-type-dr-inverse {
          description
            "Signature type DR inverse detected.";
        }
        enum signature-type-dr-plus-zrc {
          description
            "Signature types DR and XRC detected.";
        }
        enum signature-type-dr-inverse-plus-zrc {
          description
            "Signature types DR inverse and XRC detected.";
        }
      }
      description
        "This parameter specifies the topology types of the detected
         far-end signature.

         Valid response values are:

         - no signature detected
         - unknown signature
         - signature type DR detected
         - signature type ZRC detected.";
      reference
        "ITU-T G.996.2 clause F.2.2.6.1 (MELT-FES-ID)";
    }
    leaf cpe-identification-capacitive {
      type enumeration {
        enum no-cpe-detected {
          description
            "No CPE has been detected.";
        }
        enum cpe-detected {
          description
            "A CPE has been detected.";
        }
      }
      description
        "Customer Premises Equipment (CPE) detected shall be reported
         if the measured capacitance value CTR-Term is
         >= MELT-SYSC-CPE. CTR-Term shall represent the termination
         capacitance only. Therefore, the line capacitance shall be
         subtracted from the measured CTR value. For this equation to
         hold, the MELT-SYSC-CPE value should be derived from the
         nominal CPE capacitance by accounting for all tolerances and
         be set to the minimum possible measurement result.";
      reference
        "ITU-T G.996.2 clause F.2.2.7 (MELT-CPE-ID)";
    }
    leaf unreliability-indicator {
      if-feature
        "bbf-melt:melt-processing-derived-parameter-reliability";
      type bits {
        bit open-wire-failure-type {
          description
            "This sub-parameter is a five state indication of the type
             of open wire failure defined as follows:

             1) No open wire failure detected
             2) Tip and ring wires open in equal distance
             3) Tip wire open
             4) Ring wire open
             5) Undefined.

             NOTE - An error-free loop will be classified as failure
             state 2) in case that the remote end of the loop was left
             open during the measurement, or the connected CPE
             equipment could not be detected (too low parallel CPE
             system capacitance).";
          reference
            "ITU-T G.996.2 clause F.2.2.1.1 (MELT-O-WIRE-type)";
        }
        bit open-wire-failure-distance {
          description
            "This parameter represents a best-effort estimate of the
             distance of the detected open wire failure from the
             measurement point, i.e., from the central office or of
             the total loop length if no failure is detected. A priori
             knowledge of the loop characteristics is required for
             reliable estimation of the distance (see clause F.2.1.2).
             The range of valid values is from 0 to 10000 meters with
             a granularity of 1 meter.";
          reference
            "ITU-T G.996.2 clause F.2.2.1.2 (MELT-O-WIRE-DIST)";
        }
        bit short-circuit-failure-type {
          description
            "This parameter is a six-state indication of the type of
             short circuit failure defined as follows:

             1) No short circuit detected
             2) Tip and ring wires shorted to GND
             3) Tip wire shorted to GND
             4) Ring wire shorted to GND
             5) Tip and ring wires shorted to each other
             6) Undefined.";
          reference
            "ITU-T G.996.2 clause F.2.2.2.1 (MELT-S-CCT-type)";
        }
        bit leakage-identification {
          description
            "This parameter indicates a leakage to GND failure,
             classified into the following states:

             1) No leakage detected
             2) Tip and ring wire leaking to GND
             3) Tip wire leaking to GND
             4) Ring wire leaking to GND.";
          reference
            "ITU-T G.996.2 clause F.2.2.3 (MELT-LEAK-ID)";
        }
        bit resistive-fault-identification {
          description
            "This parameter indicates a resistive fault to GND
             failure, classified into the following states:

             1) No resistive fault detected
             2) Resistive fault tip and ring to GND
             3) Resistive fault tip to GND
             4) Resistive fault ring to GND.";
          reference
            "ITU-T G.996.2 clause F.2.2.4 (MELT-RFAULT-ID)";
        }
        bit foreign-voltage-type-classification {
          description
            "The foreign voltage impairment in the loop under test is
             classified into the following states:

             1) No foreign voltage detected
             2) 16 2/3 Hz AC voltage
             3) 25 Hz AC voltage
             4) 50 Hz AC voltage
             5) 60 Hz AC voltage
             6) POTS equipment (-48 volts DC)
             7) ISDN equipment (-96 volts DC)
             8) Undefined foreign voltage detected.

             This classification shall be done separately for both,
             the tip and the ring wire.";
          reference
            "ITU-T G.996.2 clause F.2.2.5.1 (MELT-FV-TYPE)";
        }
        bit foreign-voltage-level-classification {
          description
            "This parameter provides a general classification of the
             foreign voltage into the following classes:

             1) hazardous potential (e.g., power contact)
             2) foreign electromotive force
             3) other.";
          reference
            "ITU-T G.996.2 clause F.2.2.5.2 (MELT-FV-LEVEL)";
        }
        bit far-end-signature-topology-type-identification {
          description
            "This parameter specifies the topology types of the
             detected far-end signature.

             Valid response values are:

             - no signature detected
             - unknown signature
             - signature type DR detected
             - signature type ZRC detected.";
          reference
            "ITU-T G.996.2 clause F.2.2.6.1 (MELT-FES-ID)";
        }
        bit cpe-identification-capacitive {
          description
            "CPE detected shall be reported if the measured
             capacitance value CTR-Term is >= MELT-SYSC-CPE. CTR-Term
             shall represent the termination capacitance only.
             Therefore, the line capacitance shall be subtracted from
             the measured CTR value. For this equation to hold, the
             MELT-SYSC-CPE value should be derived from the nominal
             CPE capacitance by accounting for all tolerances and be
             set to the minimum possible measurement result.";
          reference
            "ITU-T G.996.2 clause F.2.2.7 (MELT-CPE-ID)";
        }
      }
      description
        "The unreliability indicator provides the set of parameters
         whose data can be considered to be unreliable.

         Possible reasons that the data is unreliable:
           - The measurement may not have been able to run, possibly
             due to external conditions.
           - The result is not reliable as the accuracy may be
             degraded due to external conditions.";
      reference
        "ITU-T G.996.2 clause F.2.2.8 (Reliability indicator)";
    }
    container melt-processing-derived-vendor-specific-status {
      if-feature
        "bbf-melt:melt-processing-derived-parameter-reliability";
      description
        "Vendor specific status associated with each MELT
         processing derived test.";
      list status {
        key "parameter";
        description
          "A list of per parameter test status.";
        leaf parameter {
          type melt-processing-derived-parameter;
          description
            "The MELT processing derived parameter.";
        }
        leaf message {
          type string;
          description
            "Vendor specific status message for each of the
             MELT processing derived parameters.";
        }
      }
    }
  }
}
