submodule bbf-fast-retransmission-profile-body {
  yang-version 1.1;
  belongs-to bbf-fast {
    prefix bbf-fast;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing retransmission profiles.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4c1; see
     the TR itself for full legal notices.";

  revision 2022-06-13 {
    description
      "Amendment 4 Corrigendum 1.
       * Approval Date:    2022-06-13
       * Publication Date: 2022-06-13.";
    reference
      "TR-355a4c1: YANG Modules for FTTdp Management
                   <https://www.broadband-forum.org/download/
                          TR-355_Amendment-4.pdf>";
  }
  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2020-01-17 {
    description
      "Amendment 2 Corrigendum 2.
       * Approval Date:    2020-01-17
       * Publication Date: 2020-01-17.";
    reference
      "TR-355a2c2: YANG Modules for FTTdp Management
                   <https://www.broadband-forum.org/download/
                          TR-355_Amendment-2.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping retransmission-parameters {
    description
      "Retransmission configuration parameters applicable to both
       upstream and downstream.";
    reference
      "ITU-T G.997.2 clause 7.2.2";
    leaf maximum-delay {
      type uint32 {
        range "4..64" {
          description
            "Defines a range from 1 to 16 milliseconds.";
        }
      }
      units "0.25 milliseconds";
      default "40";
      description
        "Defines the maximum allowed delay for retransmission (see
         clause 9.8/G.9701). The G.9701 control parameter delay_max
         is set to the same value as the maximum delay (see clause
         11.4.2.3/G.9701).";
      reference
        "ITU-T G.997.2 clause 7.2.2.1 (DELAYMAX); ITU-T G.9701
         clause 11.4.2.3.";
    }
    leaf minimum-inp-against-shine {
      type uint16 {
        range "0..520";
      }
      units "symbol periods";
      default "0";
      description
        "Defines the minimum Impulse Noise Protection (INP) against
         Single High Impulse Noise Event (SHINE). The G.9701 control
         parameter INP_min_shine is set to the same value as the
         minimum impulse noise protection against SHINE.";
      reference
        "ITU-T G.997.2 clause 7.2.2.2 (INPMIN_SHINE);
         ITU-T G.9701 clauses 9.8 and 11.4.2.4";
    }
    leaf shine-ratio {
      type uint8 {
        range "0..100" {
          description
            "Defines a range from 0.0 to 0.1.";
        }
      }
      units "0.001";
      default "0";
      description
        "Defines the SHINEratio that is used in the definition of
         the expected throughput rate (ETR). The G.9701 control
         parameter SHINEratio is set to the same value as the Single
         High Impulse Noise Event (SHINE) ratio.";
      reference
        "ITU-T G.997.2 clause 7.2.2.3 (SHINERATIO);
         ITU-T G.9701 clauses 9.8 and 11.4.2.5";
    }
    leaf minimum-inp-against-rein {
      type uint8 {
        range "0..63";
      }
      units "symbol periods";
      default "0";
      description
        "Defines the minimum Impulse Noise Protection (INP) against
         Repetitive Electrical Impulse Noise (REIN). The G.9701
         control parameter INP_min_rein is set to the same value as
         the minimum impulse noise protection against REIN.";
      reference
        "ITU-T G.997.2 clause 7.2.2.4 (INPMIN_REIN);
         ITU-T G.9701 clauses 9.8 and 11.4.2.6";
    }
    leaf rein-inter-arrival-time {
      type enumeration {
        enum hz-100 {
          value 0;
          description
            "100 Hz.";
        }
        enum hz-120 {
          value 1;
          description
            "120 Hz.";
        }
        enum hz-300 {
          value 2;
          description
            "300 Hz.";
        }
        enum hz-360 {
          value 3;
          description
            "360 Hz.";
        }
      }
      default "hz-100";
      description
        "Defines the Repetitive Electrical Impulse Noise (REIN)
         inter-arrival time. The G.9701 control parameter
         iat_rein_flag is set to the same value as the REIN
         inter-arrival time.";
      reference
        "ITU-T G.997.2 clause 7.2.2.5 (IAT_REIN);
         ITU-T G.9701 clauses 9.8 and 11.4.2.7";
    }
    leaf minimum-rfec-nfec-ratio {
      type uint8 {
        range "0..8" {
          description
            "Defines a range from 0 to 1/4.";
        }
      }
      units "1/32";
      default "0";
      description
        "Defines the minimal required ratio, RFEC/NFEC, of
         Reed-Solomon code parameters. The G.9701 control parameter
         rnratio is set to the same value as the Minimum Reed-Solomon
         RFEC/NFEC ratio.";
      reference
        "ITU-T G.997.2 clause 7.2.2.6 (RNRATIO);
         ITU-T G.9701 clause 11.4.2.8";
    }
  }

  grouping retransmission-profile {
    description
      "Defines the contents of a Retransmission Profile.";
    container downstream {
      description
        "Downstream retransmission parameters.";
      uses retransmission-parameters;
    }
    container upstream {
      description
        "Upstream retransmission parameters.";
      uses retransmission-parameters;
    }
  }
}
