submodule bbf-melt-processing-profile-body {
  yang-version 1.1;
  belongs-to bbf-melt {
    prefix bbf-melt;
  }

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing processing profiles.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping processing-profile {
    description
      "Defines the parameters contained in a processing profile.";
    container loop-resistance-classification-threshold {
      description
        "This parameter defines the limits for classification of the
         resistances to ground (GND) of the loop under test.

         The following limit values need to be defined:
          - maximum resistance for a short-circuit to GND;
          - minimum resistance for a leakage to GND;
          - maximum resistance for a leakage to GND.

         A resistance to ground measured as being:
          - Below the maximum resistance for a short circuit shall be
            interpreted as a short circuit to GND.
          - Above the maximum resistance for a short circuit and
            below the minimum resistance for a leakage shall be
            interpreted as a resistance fault to GND.
          - Above the minimum resistance for a leakage and below the
            maximum resistance for a leakage shall be interpreted as
            a leakage to GND.
          - Above the maximum resistance for a leakage shall be
            interpreted as a high impedance to GND.";
      reference
        "ITU-T G.996.2 clause F.2.1.1 (MELT-LRC-TH)";
      leaf maximum-resistance-short-circuit-to-ground {
        type uint32;
        units "0.1 kiloohms";
        description
          "The maximum resistance threshold for a short circuit to
           ground.";
      }
      leaf minimum-resistance-leakage-to-ground {
        type uint32;
        units "0.1 kiloohms";
        description
          "The minimum resistance threshold for a leakage to ground.";
      }
      leaf maximum-resistance-leakage-to-ground {
        type uint32;
        units "0.1 kiloohms";
        description
          "The maximum resistance threshold for a leakage to ground.";
      }
    }
    container loop-parameters-per-unit-length {
      description
        "The a priori knowledge of some characteristic parameters per
         Unit length of the loop under test is necessary to derive
         length or distance information from the Metallic Line Test
         Physical Medium Dependent (MELT-PMD) measurements. This
         parameter combines the set of required loop parameters:

         1) Cable characteristic capacitance per unit length between
            tip and ring. The range of valid values is from 0 to 100
            nanofarads per kilometer with a granularity of 0.1
            nanofarads per kilometer.
         2) Cable characteristic capacitance per unit length between
            tip and GND and ring and GND. The range of valid values
            is from 0 to 100 nanofarads per kilometer with a
            granularity of 0.1 nanofarads per kilometer.
         3) Cable loop DC resistance per unit length (sum of both
            wires). The range of valid values is from 50 to 400
            ohms per kilometer with a granularity of 1 ohm per
            kilometer.";
      reference
        "ITU-T G.996.2 clause F.2.1.2 (MELT-LOOP-PARAMS)";
      leaf capacitance-per-unit-length-tr {
        type uint16 {
          range "0..1000" {
            description
              "Defines a range from 0.0 to 100.0 nanofarads per
               kilometer.";
          }
        }
        units "0.1 nanofarads per kilometer";
        description
          "Cable characteristic capacitance per unit length between
           tip and ring. The range of valid values is from 0 to 100
           nanofarads per kilometer with a granularity of 0.1
           nanofarads per kilometer.";
      }
      leaf capacitance-per-unit-length-tg-rg {
        type uint16 {
          range "0..1000" {
            description
              "Defines a range from 0.0 to 100.0 nanofarads per
               kilometer.";
          }
        }
        units "0.1 nanofarads per kilometer";
        description
          "Cable characteristic capacitance per unit length between
           tip and ground (GND) and ring and GND. The range of valid
           values is from 0 to 100 nanofarads per kilometer with a
           granularity of 0.1 nanofarads per kilometer.";
      }
      leaf dc-resistance-per-unit-length {
        type uint16 {
          range "50..400";
        }
        units "ohms per kilometer";
        description
          "Cable loop DC resistance per unit length (sum of both
           wires). The range of valid values is from 50 to 400
           ohms per kilometer with a granularity of 1 ohm per
           kilometer.";
      }
    }
    leaf hazardous-dc-voltage-level {
      type uint8 {
        range "0..200";
      }
      units "volts";
      description
        "This parameter defines the level above which DC voltage shall
         be identified as hazardous. The hazardous voltage level shall
         be configurable between 0 and 200 volts with a granularity of
         1 volt.";
      reference
        "ITU-T G.996.2 clause F.2.1.3 (MELT-HDCV-L)";
    }
    leaf hazardous-ac-voltage-level {
      type uint8 {
        range "0..200";
      }
      units "volts RMS";
      description
        "This parameter defines the level above which AC voltage shall
         be identified as hazardous. The hazardous voltage level shall
         be configurable between 0 and 200 volts RMS with a
         granularity of 1 volt RMS.";
      reference
        "ITU-T G.996.2 clause F.2.1.4 (MELT-HACV-L)";
    }
    leaf foreign-emf-dc-voltage-level {
      type uint8 {
        range "0..50";
      }
      units "volts";
      description
        "This parameter defines the level above which a DC voltage
         shall be identified as a foreign Electromagnetic Field (EMF).
         The foreign EMF voltage level shall be configurable between
         0 and 50 volts with a granularity of 1 volt.";
      reference
        "ITU-T G.996.2 clause F.2.1.5 (MELT-FDCV-L)";
    }
    leaf foreign-emf-ac-voltage-level {
      type uint8 {
        range "0..50";
      }
      units "volts RMS";
      description
        "This parameter defines the level above which an AC voltage
         shall be identified as a foreign Electromagnetic Field (EMF).
         The foreign EMF voltage level shall be configurable between
         0 and 50 volts RMS with a granularity of 1 volt RMS.";
      reference
        "ITU-T G.996.2 clause F.2.1.6 (MELT-FACV-L)";
    }
    leaf system-capacitance-cpe-side {
      type uint16 {
        range "0..20000" {
          description
            "Defines a range from 0.0 to 2000.0 nanofarads.";
        }
      }
      units "0.1 nanofarads";
      description
        "This parameter is the expected value of the system
         capacitance at the Customer Premises Equipment (CPE) side as
         it appears in parallel between tip and ring in a
         corresponding Metallic Line Test (MELT) measurement.
         A priori knowledge of this capacitance improves accuracy of
         the results and offers additional degrees for
         interpretation. The range of valid values is from 0 to 2
         microfarads with a granularity of 0.1 nanofarads.";
      reference
        "ITU-T G.996.2 clause F.2.1.7 (MELT-SYSC-CPE)";
    }
  }
}
