module bbf-frame-processing {
  yang-version 1.1;
  namespace "urn:bbf:yang:bbf-frame-processing";
  prefix bbf-fp;

  import bbf-yang-types {
    prefix bbf-yang;
  }

  organization
    "Broadband Forum <https://www.broadband-forum.org>
     Common YANG Work Area";
  contact
    "Comments or questions about this Broadband Forum YANG module
     should be directed to <mailto:help@broadband-forum.org>.

     Editor:      Shiya Ashraf, Nokia

     Editor:      Nick Hancock, Adtran

     Editor:      Kevin Noll, CableLabs

     Editor:      Ludwig Pauwels, Nokia

     PS Leader:   Aihua Guo, Futurewei

     WA Director: Joey Boyd, Adtran

     WA Director: Sven Ooghe, Nokia";
  description
    "This module contains a collection of YANG definitions for
     supporting the Broadband Forum requirements on the management of
     sub-interfaces as applicable to access network equipment. As
     such, this module is specific to access network equipment (e.g.,
     BBF-specified Access Nodes and FTTdp DPUs).

     Specifically, this module defines generic groupings that can be
     used when defining frame processing data nodes.

     Copyright (c) 2017-2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a8; see
     the TR itself for full legal notices.";

  revision 2024-11-11 {
    description
      "Amendment 8.
       * Approval Date:    2024-11-11.
       * Publication Date: 2024-11-11.";
    reference
      "TR-383a8: Common YANG Modules for Access Networks
                 <https://www.broadband-forum.org/technical/download/
                          TR-383_Amendment-8.pdf>";
  }
  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }

  grouping frame-processing {
    description
      "Provides a generic framework of frame-processing, i.e., define
       the data nodes supporting a list of ingress rules with a
       corresponding ingress-rewrite, and an egress-rewrite.

       The frame processing refers to both directions:
       - Ingress, which refers to frames received from the
         lower-layer interface.
       - Egress, which refers to frames received from a higher-layer
         interface, or from a forwarder, and to be transmitted to the
         lower-layer interface.
       - In the ingress direction classification criteria identify
         whether a received frame shall be offered to this
         sub-interface.
       - For both the ingress and egress direction tag manipulations
         can be supported.";
    container ingress-rule {
      description
        "Data nodes to manage rules to classify and manipulate ingress
         frames to a sub-interface.";
      list rule {
        key "name";
        min-elements 1;
        description
          "A rule contains a classification and for frames that
           match this classification it specifies an ingress tag
           manipulation action.

           The definition is: first match, then stop searching for
           matches with other rules, then execute the
           ingress-rewrite actions specified in this rule.";
        leaf name {
          type bbf-yang:string-ascii64;
          description
            "The rule name.";
        }
        leaf priority {
          type uint16 {
            range "1..max";
          }
          description
            "This field indicates the priority for applying the
             match criteria of this rule against the priority of
             match criteria of other rules of this and other
             sub-interfaces on the same parent-interface.

             The higher the value, the lower the priority, i.e.,
             priority 1 is the highest priority.

             Note that priorities of rules do not have to be unique
             within a lower-layer interface. For example, if there
             is no overlap in the 'flexible-match' criteria of a
             different sub-interfaces having the same lower-layer
             interface, then the configuration is still unambiguous.
             If different sub-interfaces with the same lower-layer
             interface are configured such that there is overlap
             between their flexible-match criteria, then unambiguity
             is achieved by configuring the rules with different
             priorities. If the priority is configured equal,
             despite having overlapping match criteria, then the
             device's behavior is undefined, meaning, it can be
             different in different devices, even more it can be
             different in single device over time.

             Note that although priority is not a mandatory leaf,
             it is strongly recommended that it be configured to
             ensure a deterministic behavior of applying rules of
             this and other sub-interfaces on the same parent
             interface when multiple match criteria apply.";
        }
        container ingress-rewrite {
          description
            "Data nodes to manage ingress rewrite, which refers to the
             supported tag manipulations before the frame is offered
             to a higher-layer interface or to a forwarder.";
        }
      }
    }
    container egress-rewrite {
      description
        "Data nodes to manage egress rewrite, whereby 'egress' refers
         to the frames sent from the sub-interface towards the the
         lower-layer in the interface stack, i.e., in the direction of
         the physical interface and 'rewrite' refers to the supported
         tag manipulations.";
    }
  }
}
