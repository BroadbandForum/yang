submodule bbf-vdsl-xtu-channel-performance-body {
  yang-version 1.1;
  belongs-to bbf-vdsl {
    prefix bbf-vdsl;
  }

  import bbf-yang-types {
    prefix bbf-yang;
  }
  import ietf-yang-types {
    prefix yang;
  }
  include bbf-vdsl-base-body;

  organization
    "Broadband Forum <https://www.broadband-forum.org>
     Common YANG Work Area";
  contact
    "Comments or questions about this Broadband Forum YANG module
     should be directed to <mailto:help@broadband-forum.org>.

     Editor:      Ken Kerpez, ASSIA, Inc.

     Editor:      Joey Boyd, Adtran

     PS Leader:   Joey Boyd, Adtran

     WA Director: Sven Ooghe, Nokia

     WA Director: Joey Boyd, Adtran";
  description
    "This submodule contains a collection of YANG definitions for
     managing Broadband Forum TR-252i3 clause 7.2 xDSL Transceiver
     Unit (xTU) Channel Performance.

     Copyright (c) 2016-2022 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a4; see
     the TR itself for full legal notices.";

  revision 2022-05-23 {
    description
      "Amendment 4.
       * Approval Date:    2022-05-23
       * Publication Date: 2022-05-23.";
    reference
      "TR-355a4: YANG Modules for FTTdp Management
                   <https://www.broadband-forum.org/download/
                          TR-355_Amendment-4.pdf>";
  }
  revision 2020-10-13 {
    description
      "Amendment 3.
       * Approval Date:    2020-10-13
       * Publication Date: 2020-10-13.";
    reference
      "TR-355a3: YANG Modules for FTTdp Management
                   <https://www.broadband-forum.org/download/
                          TR-355_Amendment-3.pdf>";
  }
  revision 2019-10-21 {
    description
      "Amendment 2 Corrigendum 1.
       * Approval Date:    2019-10-21
       * Publication Date: 2019-10-21.";
    reference
      "TR-355a2c1: YANG Modules for FTTdp Management
                   <https://www.broadband-forum.org/download/
                          TR-355_Amendment-2.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping xtu-channel-performance-c {
    description
      "The xDSL Transceiver Unit (xTU) Channel (near-end) performance
       parameters represent channel performance related data for a
       particular channel associated with a particular xDSL
       Transceiver Unit - Central office (xTU-C).";
    leaf measured-time {
      type uint32;
      units "seconds";
      description
        "Reports the amount of time, measured in seconds, that
         statistics for this interval have been counted.";
      reference
        "ITU-T G.997.2 clauses 7.7.1 and 7.8.1";
    }
    leaf invalid-data-flag {
      type boolean;
      description
        "Reports the validity of the corresponding performance
         monitoring data.  true = invalid.";
      reference
        "ITU-T G.997.2 clauses 7.7.2 and 7.8.2";
    }
    leaf code-violations-c {
      type bbf-yang:performance-counter32;
      description
        "This parameter is a count of CRC-8 anomalies (the number
         of incorrect Cyclic Redundancy Check (CRC)) occurring in the
         bearer channel during the accumulation period. This parameter
         is subject to inhibiting - see ITU-T G.997.1 clause
         7.2.7.13.";
      reference
        "ITU-T G.997.1 clause 7.2.2.1.1 (CV-C)";
    }
    leaf forward-error-corrections-c {
      type bbf-yang:performance-counter32;
      description
        "This parameter is a count of Forward Error Correction (FEC)
         anomalies (the number of corrected code words) occurring in
         the bearer channel during the accumulation period. This
         parameter is subject to inhibiting.";
      reference
        "ITU-T G.997.1 clauses 7.2.2.1.2 (FEC-C) and 7.2.7.13";
    }
    leaf uncorrected-dtu-c {
      type bbf-yang:performance-counter32;
      description
        "This parameter is a count of rtx-uc anomalies (the number of
         uncorrected Data Transfer Units (DTU)) occurring in the
         bearer channel during the accumulation period. This parameter
         only applies to systems supporting ITU-T G.998.4. This
         parameter is subject to inhibiting.";
      reference
        "ITU-T G.997.1 clauses 7.2.2.1.3 (RTXUC-C) and 7.2.7.13;
         ITU-T G.998.4 clause 12";
    }
    leaf retransmitted-dtu-c {
      type bbf-yang:performance-counter32;
      description
        "This parameter is a count of rtx-tx anomalies (the number of
         retransmitted Data Transfer Units (DTU)) occurring in the
         bearer channel during the accumulation period. This parameter
         only applies to systems supporting ITU-T G.998.4. This
         parameter is subject to inhibiting.";
      reference
        "ITU-T G.997.1 clauses 7.2.2.1.4 (RTXTX-C) and 7.2.7.13;
         ITU-T G.998.4 clause 12";
    }
  }

  grouping xtu-channel-performance-cfe {
    description
      "The xDSL Transceiver Unit (xTU) Channel far-end performance
       parameters represent channel performance related data for a
       particular channel associated with a particular xDSL
       Transceiver Unit - Remote side (xTU-R).";
    leaf measured-time {
      type uint32;
      units "seconds";
      description
        "Reports the amount of time, measured in seconds, that
         statistics for this interval have been counted.";
      reference
        "ITU-T G.997.2 clauses 7.7.1 and 7.8.1";
    }
    leaf invalid-data-flag {
      type boolean;
      description
        "Reports the validity of the corresponding performance
         monitoring data.  true = invalid.";
      reference
        "ITU-T G.997.2 clauses 7.7.2 and 7.8.2";
    }
    leaf code-violations-cfe {
      type bbf-yang:performance-counter32;
      description
        "This parameter is a count of Far-End Block Error (FEBE)
         anomalies occurring in the bearer channel during the
         accumulation period. This parameter is subject to
         inhibiting.";
      reference
        "ITU-T G.997.1 clauses 7.2.2.2.1 (CV-CFE) and 7.2.7.13";
    }
    leaf forward-error-corrections-cfe {
      type bbf-yang:performance-counter32;
      description
        "This parameter is a count of Far-End Forward Error Correction
         (FFEC) anomalies occurring in the bearer channel during the
         accumulation period. This parameter is subject to
         inhibiting.";
      reference
        "ITU-T G.997.1 clauses 7.2.2.2.2 (FEC-CFE) and 7.2.7.13";
    }
    leaf uncorrected-dtu-cfe {
      type bbf-yang:performance-counter32;
      description
        "This parameter is a count of far-end rtx-uc anomalies (the
         number of uncorrected Data Transfer Units (DTU)) occurring in
         the bearer channel during the accumulation period. This
         parameter only applies to systems supporting ITU-T G.998.4.
         This parameter is subject to inhibiting.";
      reference
        "ITU-T G.997.1 clauses 7.2.2.2.3 (RTXUC-CFE) and 7.2.7.13;
         ITU-T G.998.4 clause 12";
    }
    leaf retransmitted-dtu-cfe {
      type bbf-yang:performance-counter32;
      description
        "This parameter is a count of far-end rtx-tx anomalies (the
         number of retransmitted Data Transfer Units (DTU)) occurring
         in the bearer channel during the accumulation period. This
         parameter only applies to systems supporting ITU-T G.998.4.
         This parameter is subject to inhibiting.";
      reference
        "ITU-T G.997.1 clauses 7.2.2.2.4 (RTXTX-CFE) and 7.2.7.13;
         ITU-T G.998.4 clause 12";
    }
  }

  grouping performance-history-15min-parameters {
    description
      "Defines common parameters required of historical
       performance counters across 15 minute intervals.";
    leaf number-of-intervals {
      type performance-15min-interval;
      description
        "The total number of 15 minute PM intervals for which data
         was collected.";
    }
    leaf non-valid-intervals {
      type performance-15min-interval;
      description
        "The number of 15 minute PM intervals for which the data
         is considered to be invalid or incomplete.";
    }
  }

  grouping performance-history-24hr-parameters {
    description
      "Defines common parameters required of historical
       performance counters across 24 hour intervals.";
    leaf number-of-intervals {
      type performance-24hr-interval;
      description
        "The total number of 24 hour performance monitoring
         intervals for which data was collected.";
    }
    leaf non-valid-intervals {
      type performance-24hr-interval;
      description
        "The number of 24 hour performance monitoring
         intervals for which the data is considered to be
         invalid or incomplete.";
    }
  }

  grouping xtu-channel-time-stamp {
    description
      "Time stamp of channel performance parameters.";
    leaf time-stamp {
      type yang:date-and-time;
      description
        "Reports the start date/time for this interval.";
      reference
        "ITU-T G.997.2 clause 7.8.3";
    }
  }
}
