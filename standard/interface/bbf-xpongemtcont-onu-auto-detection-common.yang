module bbf-xpongemtcont-onu-auto-detection-common {
  yang-version 1.1;
  namespace "urn:bbf:yang:bbf-xpongemtcont-onu-auto-detection-common";
  prefix bbf-xpongemtcont-onu-adc;

  import bbf-xpon-types {
    prefix bbf-xpon-types;
  }
  import bbf-xpongemtcont {
    prefix bbf-xpongemtcont;
  }

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on the management of
     Passive Optical Network (PON) interfaces. As such, this module
     is specific to access network equipment (e.g., BBF-specified
     Access Nodes and FTTdp DPUs).

     Specifically, this module defines types and groupings for use
     when defining data nodes for managing G-PON Encapsulation Method
     (GEM) ports and T-CONTs when the ONU xPON type is auto-detected.

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }

  grouping traffic-descriptor-profile-refs {
    description
      "Per xPON type Traffic Descriptor Profile references when ONU
       xPON type is auto-detected.";
    list traffic-descriptor-profile-ref {
      key "xpon-type";
      description
        "A Traffic Descriptor Profile reference that can be used
         for a specific xPON type, and only for this type.";
      leaf xpon-type {
        type identityref {
          base bbf-xpon-types:xpon-type-base;
        }
        description
          "The xPON type of the ONU that is acceptable.";
      }
      leaf profile-ref {
        type leafref {
          path "/bbf-xpongemtcont:xpongemtcont/bbf-xpongemtcont:"
             + "traffic-descriptor-profiles/bbf-xpongemtcont:"
             + "traffic-descriptor-profile/bbf-xpongemtcont:name";
        }
        description
          "References an existing traffic descriptor profile.";
      }
    }
  }

  grouping alloc-ids {
    description
      "Per xPON type Allocation Identifier (Alloc-ID) when ONU xPON
       type is auto-detected.";
    list alloc-id {
      key "xpon-type";
      description
        "An Alloc-ID that can be used for a specific xPON type, and
         only for this type .";
      leaf xpon-type {
        type identityref {
          base bbf-xpon-types:xpon-type-base;
        }
        description
          "The xPON type of the ONU that is acceptable.";
      }
      leaf alloc-id {
        type bbf-xpon-types:alloc-id;
        description
          "Transmission Container (T-CONT) Allocation Identifier
           (Alloc-ID). When configured this is the value which must
           actually be used between the Optical Line Termination
           (OLT) device and Optical Network Unit (ONU) device for
           this T-CONT. For GPON the value should be in [256..4095]
           and for XG-PON, XGS-PON and NG-PON2 it should be in
           [1024..16383].";
        reference
          "ITU-T G.984.3 Clause 5.5.3;
           ITU-T G.987.3 Clause 6.4.3;
           ITU-T G.9807.1 Clause C.6.1.5.7;
           ITU-T G.989.3 Clause 6.1.5.7";
      }
    }
  }

  grouping gemport-ids {
    description
      "Per xPON type GEM (G-PON Encapsulation Method (GEM) port
       IDs when ONU xPON type is auto-detected.";
    list gemport-id {
      key "xpon-type";
      description
        "An GEM port ID that can be used for a specific xPON type,
         and only for this type.";
      leaf xpon-type {
        type identityref {
          base bbf-xpon-types:xpon-type-base;
        }
        description
          "The xPON type of the ONU that is acceptable.";
      }
      leaf gemport-id {
        type uint32;
        description
          "ID of GPON Encapsulation Method (GEM) port. When
           configured this is the value which must actually be used
           between the Optical Line Termination (OLT) device and
           Optical Network Unit (ONU) device for this GEM port and
           this xPON type. For GPON the value should be in [0..4095]
           and not conflicting with the 'management-gemport-id', for
           XG-PON it should be in [1023..65534] and for XGS-PON and
           NG-PON2 it should be in [1021..65534].";
        reference
          "ITU-T G.984.3 Clause 5.5.5;
           ITU-T G.987.3 Clause 6.4.4;
           ITU-T G.9807.1 Clause C.6.1.5.8;
           ITU-T G.989.3 Clause 6.1.5.8";
      }
    }
  }
}
