module bbf-xpon-power-saving {
  yang-version 1.1;
  namespace "urn:bbf:yang:bbf-xpon-power-saving";
  prefix bbf-xpon-pwr-sav;

  import ietf-hardware {
    prefix hw;
  }
  import bbf-hardware-types {
    prefix bbf-hwt;
  }
  import bbf-power-saving {
    prefix bbf-pwr-sav;
  }
  import bbf-xpon-power-saving-common {
    prefix bbf-xpon-pwr-savc;
  }

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran

     PS Leader:   Sven Ooghe, Nokia

     WA Director: Marta Seda, Calix

     WA Director: Herman Verbueken, Nokia";
  description
    "This module contains a collection of YANG definitions for
     supporting the Broadband Forum requirements on the management of
     Passive Optical Network (PON) interfaces. As such, this module
     is specific to access network equipment (e.g., BBF-specified
     Access Nodes and FTTdp DPUs).

     Specifically, this module models data to manage xPON power
     saving in the OLT, such as power saving on xPON transceivers
     and transceiver links, using various criteria.

     Copyright (c) 2018-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3a1; see
     the TR itself for full legal notices.";

  revision 2026-11-02 {
    description
      "Issue 3 Amendment 1.
       * Approval Date:    2026-11-02.
       * Publication Date: 2026-11-02.";
    reference
      "TR-385i3a1: YANG Modules for PON Management
               <https://www.broadband-forum.org/technical/download/
                        TR-385_Issue-3_Amendment-1.pdf>";
  }

  augment "/bbf-pwr-sav:power-saving" {
    if-feature "bbf-xpon-pwr-savc:xpon-transceiver-power-saving";
    description
      "Augments system power saving configuration with xpon
       transceiver power saving data nodes.";
    container xpon-transceiver {
      presence
        "Presence of this container indicates that global xPON
         transceiver power saving control is managed on this OLT.";
      description
        "xPON transceiver power saving configuration data nodes.";
      uses
        bbf-xpon-pwr-savc:power-saving-xpon-transceiver-config-data;
    }
  }

  augment "/hw:hardware/hw:component/bbf-pwr-sav:power-saving" {
    when "derived-from-or-self(../hw:class,'bbf-hwt:transceiver')" {
      description
        "This augment is only applicable for a transceiver.";
    }
    if-feature "bbf-xpon-pwr-savc:xpon-transceiver-power-saving";
    description
      "Augments specific xPON transceivers with power saving
       configuration. Configuration at this level overrules any
       power saving data configured at the system level for xPON
       transceivers. The data nodes of this augment are only
       relevant for transceivers used for xPON. It they are
       configured for a transceiver not used fof xPON, they will
       be silently ignored.";
    uses bbf-xpon-pwr-savc:power-saving-xpon-transceiver-config-data;
  }

  augment "/hw:hardware/hw:component/bbf-pwr-sav:power-saving/"
        + "bbf-pwr-sav:state" {
    when "derived-from-or-self(../../hw:class,'bbf-hwt:transceiver')
          or derived-from-or-self(../../hw:class,
          'bbf-hwt:transceiver-link')" {
      description
        "This augment is only applicable for an xPON transceiver or
         transceiver-link.";
    }
    if-feature "bbf-xpon-pwr-savc:xpon-transceiver-power-saving";
    description
      "Augments a hardware component with xPON transceiver power
       saving state data.";
    leaf-list applied-xpon-criteria {
      type identityref {
        base bbf-xpon-pwr-savc:power-saving-xpon-transceiver-criteria;
      }
      description
        "State data node showing which power saving criteria is
         currently met for this hardware component.";
    }
  }
}
