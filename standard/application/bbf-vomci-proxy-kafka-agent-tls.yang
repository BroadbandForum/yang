module bbf-vomci-proxy-kafka-agent-tls {
  yang-version 1.1;
  namespace "urn:bbf:yang:bbf-vomci-proxy-kafka-agent-tls";
  prefix bbf-vomci-proxy-ka-tls;

  import bbf-vomci-proxy {
    prefix bbf-vomci-proxy;
  }
  import bbf-vomci-proxy-kafka-agent {
    prefix bbf-vomci-proxy-ka;
  }
  import ietf-tcp-client {
    prefix tcpc;
  }
  import ietf-tls-client {
    prefix tlsc;
  }

  organization
    "Broadband Forum <https://www.broadband-forum.org>
     SDN/NFV Work Area";
  contact
    "Comments or questions about this Broadband Forum YANG module
     should be directed to <mailto:help@broadband-forum.org>.

     Editor:      Andre Brizido, Altice Labs

     PS Leader:   Ken Kerpez, DZS

     WA Director: Mengmeng Li, China Mobile

     WA Director: Bruno Cornaglia, Vodafone

     WA Director: Haomian Zheng, Huawei";
  description
    "This module contains a collection of YANG definitions for
     supporting the Broadband Forum requirements for vOMCI Kafka
     transport over TLS functionality as described in TR-451.

     Copyright (c) 2019-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451a1; see
     the TR itself for full legal notices.";

  revision 2025-02-03 {
    description
      "Amendment 1.
       * Approval Date:    2025-02-03.
       * Publication Date: 2025-02-03.";
    reference
      "TR-451a1: vOMCI Specification
               <https://www.broadband-forum.org/technical/download/
                        TR-451_Amendment-1.pdf>";
  }

  augment "/bbf-vomci-proxy:vomci"
        + "/bbf-vomci-proxy:remote-nf"
        + "/bbf-vomci-proxy:nf-client"
        + "/bbf-vomci-proxy:initiate"
        + "/bbf-vomci-proxy:remote-server"
        + "/bbf-vomci-proxy:transport"
        + "/bbf-vomci-proxy-ka:kafka"
        + "/bbf-vomci-proxy-ka:kafka-agent"
        + "/bbf-vomci-proxy-ka:access-point"
        + "/bbf-vomci-proxy-ka:kafka-agent-transport-parameters"
        + "/bbf-vomci-proxy-ka:tcp-client-options" {
    description
      "The Kafka connection parameters for TLS transport.";
    case tls-transport {
      description
        "Selection for TLS transport.";
      container tcp-client-parameters {
        description
          "The TCP configuration.";
        uses tcpc:tcp-client-grouping;
      }
      container tls-client-parameters {
        description
          "The TLS configuration.";
        uses tlsc:tls-client-grouping;
      }
    }
  }
}
