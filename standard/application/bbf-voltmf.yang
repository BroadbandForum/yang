module bbf-voltmf {
  yang-version 1.1;
  namespace "urn:bbf:yang:bbf-voltmf";
  prefix bbf-voltmf;

  import bbf-device-aggregation {
    prefix bbf-dev-agg;
  }
  import bbf-device-types {
    prefix bbf-dvct;
  }
  import bbf-network-function {
    prefix bbf-nf;
  }
  import bbf-network-function-client {
    prefix bbf-nfc;
  }
  import bbf-network-function-types {
    prefix bbf-nft;
  }
  import bbf-voltmf-common {
    prefix bbf-voltmf-c;
  }
  import bbf-voltmf-message-monitor {
    prefix bbf-voltmf-msg-mon;
  }
  import bbf-vomci-common {
    prefix bbf-vomci-c;
  }
  import bbf-xpon-types {
    prefix bbf-xpon-types;
  }
  import bbf-yang-types {
    prefix bbf-yang;
  }
  import ietf-yang-schema-mount {
    prefix yangmnt;
  }

  organization
    "Broadband Forum <https://www.broadband-forum.org>
     SDN/NFV Work Area";
  contact
    "Comments or questions about this Broadband Forum YANG module
     should be directed to <mailto:help@broadband-forum.org>.

     Editor:      Andre Brizido, Altice Labs

     PS Leader:   Ken Kerpez, DZS

     WA Director: Mengmeng Li, China Mobile

     WA Director: Bruno Cornaglia, Vodafone

     WA Director: Haomian Zheng, Huawei";
  description
    "This module contains a collection of YANG definitions for
     supporting the Broadband Forum requirements for the virtual
     OLT management functionality (vOLTMF) functionality as
     described in TR-451.

     Copyright (c) 2019-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451a1; see
     the TR itself for full legal notices.";

  revision 2025-02-03 {
    description
      "Amendment 1.
       * Approval Date:    2025-02-03.
       * Publication Date: 2025-02-03.";
    reference
      "TR-451a1: vOMCI Specification
               <https://www.broadband-forum.org/technical/download/
                        TR-451_Amendment-1.pdf>";
  }
  revision 2022-06-07 {
    description
      "Issue 1.
       * Approval Date:    2022-06-07.
       * Publication Date: 2022-06-07.";
    reference
      "TR-451: vOMCI Specification
               <https://www.broadband-forum.org/technical/download/
                        TR-451_Issue-1.pdf>";
  }

  // 

  augment "/bbf-dev-agg:devices/bbf-dev-agg:device" {
    when "derived-from-or-self(bbf-dev-agg:type,'bbf-dvct:onu')" {
      description
        "ONU specific data needed for management of the ONU via vOMCI.
         Only applicable if the device type is an ONU or derivative
         thereof.";
    }
    description
      "The management plane augmentation for ONU devices.";
    container vomci-onu-management {
      description
        "The ONU management data needed for vOMCI solutions.";
      leaf onu-management-chain-selection {
        type enumeration {
          enum vomci-policy {
            description
              "Identifies that the ONU management chain is computed
               using a policy to select the vOMCI function instance.";
          }
          enum configured {
            description
              "Identifies that the ONU management chain is configured
               by an external entity.";
          }
          enum vomci-function {
            description
              "Identifies that the ONU management chain is computed
               using the type of vOMCI function to select the vOMCI
               function instance.";
          }
        }
        mandatory true;
        description
          "The option used to determine the ONU management chain.";
      }
      leaf vomci-function {
        type bbf-yang:string-ascii64;
        description
          "Data nodes describing the VNF 'flavor' (not instance) being
           used for the ONU. For example, vendor or version info.";
      }
      list onu-management-chain {
        key "nf-type nf-instance";
        ordered-by user;
        leaf nf-type {
          type identityref {
            base bbf-nft:nf-type;
          }
          description
            "The type of NF.";
        }
        leaf nf-instance {
          type bbf-yang:string-ascii64;
          description
            "The name of the NF.";
        }
        description
          "The ordered list of ONU Management Proxy, vOMCI function,
           vOMCI Proxy and OLT entities to use for this ONU's
           management. When the ONU Management Proxy is not deployed,
           the list is ordered from the vOMCI function to the OLT
           inclusive. If the value of the leaf 'onu-management-chain-
           selection' is set to 'vomci-function' then list contains
           the vOMCI function instance. When the ONU Management Proxy
           is deployed, the list is ordered with the ONU Management
           Proxy and then the OLT.";
      }
      container statistics {
        description
          "Counters for per ONU messages sent between the entity and
           vOMCI function or ONU Management Proxy.";
        uses bbf-voltmf-msg-mon:voltmf-message-statistics;
      }
    }
  }

  container voltmf {
    description
      "Data nodes associated with the vOLTMF.";
    container nf-topology {
      description
        "The VNFs, VNF instances and network function links that
         cannot be discovered.

         When an ONU Management Proxy is not deployed, the vOLTMF has
         knowledge of:
           VNFs: vOMCI Function, vOMCI Proxy
           VNF Instances and links of Network Functions:
             vOMCI Function, vOMCI Proxy

         When an ONU Management Proxy is deployed, the vOLTMF has
         knowledge of:
           VNFs: vOMCI Function, vOMCI Proxy, ONU Management Proxy
           VNF Instances and links of Network Functions: vOMCI Proxy,
             ONU Management Proxy.";
      uses bbf-nf:nf-topology {
        augment "vnf-instance" {
          description
            "Add specific data nodes for the vOLTMF.";
          container data {
            description
              "The data nodes of the device's schema.";
            yangmnt:mount-point "device-yang-library" {
              description
                "The YANG library associated with the device.";
            }
          }
        }
      }
    }
    container onu-vomci-assignment-policy {
      description
        "The policy rules to use to associate an ONU with a list of
         vOMCI functions.";
      uses bbf-voltmf-c:onu-vomci-assignment-policy;
    }
    container remote-nf {
      presence "Enables access to remote network functions";
      description
        "Data nodes to manage remote network functions (NF).";
      container nf-client {
        description
          "Data nodes to manage the clients of the network function.";
        leaf enabled {
          type boolean;
          default "true";
          description
            "Administratively enable the use of the client
             connectivity capability to the network function.";
        }
        uses bbf-nfc:nf-client;
      } //nf-client
    }
    container statistics {
      config false;
      description
        "Counters for the vOLTMF messages sent between the vOLTMF and
         vOMCI function or ONU Management Proxy that are not targeted
         to an ONU.";
      action reset {
        description
          "Reset the statistics counters.";
      }
      uses bbf-voltmf-msg-mon:voltmf-message-statistics;
    }
  }

  // Notifications

  notification onu-discovery-result {
    description
      "Reports the result of the discovery procedure for an ONU.";
    leaf onu-serial-number {
      type bbf-xpon-types:onu-serial-number;
      description
        "The TC layer ONU serial number of the discovered ONU.";
    }
    leaf discovery-result {
      type enumeration {
        enum successful {
          description
            "The ONU discovery procedure was successful.";
        }
        enum failed-no-connectivity {
          description
            "The ONU discovery procedure failed to discover the ONU
             because the ONU is not reachable.";
        }
        enum failed-unknown-onu {
          description
            "The ONU discovery procedure failed to discover the ONU
             because the ONU is not known to the vOLTMF.";
        }
      }
      mandatory true;
      description
        "The result of the discovery process for this ONU.";
    }
    anydata device-info {
      description
        "The device information obtained as the result of the
         discovery process.";
    }
    anydata software-info {
      description
        "The software information obtained as the result of the
         discovery process.";
    }
  }

  augment "/bbf-voltmf:voltmf"
        + "/bbf-voltmf:remote-nf"
        + "/bbf-voltmf:nf-client"
        + "/bbf-voltmf:initiate"
        + "/bbf-voltmf:remote-server" {
    description
      "Augment per endpoint statistics on the remote server.";
    container statistics {
      config false;
      description
        "Statistics associated with the remote server.";
      action reset {
        description
          "Reset the statistics.";
      }
      uses bbf-vomci-c:endpoint-message-statistics;
    }
  }
}
