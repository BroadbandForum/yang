module bbf-vomci-proxy {
  yang-version 1.1;
  namespace "urn:bbf:yang:bbf-vomci-proxy";
  prefix bbf-vomci-proxy;

  import bbf-network-function-client {
    prefix bbf-nfc;
  }
  import bbf-network-function-server {
    prefix bbf-nfs;
  }
  import bbf-omci-message-retransmission {
    prefix bbf-omci-mr;
  }
  import bbf-vomci-common {
    prefix bbf-vomci-c;
  }
  import bbf-vomci-types {
    prefix bbf-vomcit;
  }
  import bbf-yang-types {
    prefix bbf-yang;
  }

  organization
    "Broadband Forum <https://www.broadband-forum.org>
     SDN/NFV Work Area";
  contact
    "Comments or questions about this Broadband Forum YANG module
     should be directed to <mailto:help@broadband-forum.org>.

     Editor:      Andre Brizido, Altice Labs

     PS Leader:   Ken Kerpez, DZS

     WA Director: Mengmeng Li, China Mobile

     WA Director: Bruno Cornaglia, Vodafone

     WA Director: Haomian Zheng, Huawei";
  description
    "This module contains a collection of YANG definitions for
     supporting the Broadband Forum requirements for vOMCI Proxy
     functionality as described in TR-451.

     Copyright (c) 2019-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451a1; see
     the TR itself for full legal notices.";

  revision 2025-02-03 {
    description
      "Amendment 1.
       * Approval Date:    2025-02-03.
       * Publication Date: 2025-02-03.";
    reference
      "TR-451a1: vOMCI Specification
               <https://www.broadband-forum.org/technical/download/
                        TR-451_Amendment-1.pdf>";
  }
  revision 2022-06-07 {
    description
      "Issue 1.
       * Approval Date:    2022-06-07.
       * Publication Date: 2022-06-07.";
    reference
      "TR-451: vOMCI Specification
               <https://www.broadband-forum.org/technical/download/
                        TR-451_Issue-1.pdf>";
  }

  // Features

  feature nf-client {
    description
      "Indicates that client connectivity to network function
       endpoints is supported.";
  }

  feature nf-server {
    description
      "Indicates that server connectivity to network function
       endpoints is supported.";
  }

  container vomci {
    description
      "Data nodes associated with the vOMCI Proxy.";
    leaf message-timeout {
      type uint16 {
        range "10..max";
      }
      units "seconds";
      default "900";
      description
        "The maximum number of seconds for a response to be
         received to a transmitted vOMCI message. The timeout is
         used to clean up stale vOMCI messages. The timeout is
         only applicable when OMCI message retransmission
         capability is not currently enabled for this entity.";
    }
    container omci-message-retransmission {
      if-feature "bbf-omci-mr:omci-message-retransmission";
      description
        "OMCI message retransmission capability data.";
      uses bbf-omci-mr:omci-message-retransmission;
    } //OMCI message retransmission capability
    container remote-nf {
      presence "Enables access to remote network functions";
      description
        "Data nodes to manage remote network functions (NF).";
      container nf-client {
        if-feature "bbf-vomci-proxy:nf-client";
        description
          "Data nodes to manage the clients of the network function.";
        leaf enabled {
          type boolean;
          default "true";
          description
            "Administratively enable the use of client connectivity
             capability to connect to network function endpoints.";
        }
        uses bbf-nfc:nf-client;
      } //nf-client
      container nf-server {
        if-feature "bbf-vomci-proxy:nf-server";
        description
          "Data nodes to manage the server of the network function.";
        leaf enabled {
          type boolean;
          default "true";
          description
            "Administratively enable the use of server connectivity
             capability to connect to network function endpoints.";
        }
        uses bbf-nfs:nf-server;
      } //nf-server
    }
    container statistics {
      config false;
      description
        "The OMCI function statistics.";
      action reset {
        description
          "Reset the counters of the statistics.";
      }
      uses bbf-omci-mr:omci-message-retransmission-statistics {
        if-feature "bbf-omci-mr:omci-message-retransmission";
      }
    }
    container managed-onus {
      description
        "The ONUs that are being managed by this entity.";
      action create-onu {
        description
          "Create an ONU within the vOMCI Proxy.";
        input {
          leaf name {
            type bbf-vomcit:onu-name;
            description
              "The unique name of the ONU.";
          }
          leaf xpon-onu-type {
            type identityref {
              base bbf-vomcit:xpon-onu-type;
            }
            description
              "The ONU's xPON type.";
          }
        }
      }
      list managed-onu {
        key "name";
        config false;
        description
          "An ONU that is being managed by this entity.";
        leaf name {
          type bbf-vomcit:onu-name;
          description
            "The unique name of the ONU.";
        }
        leaf xpon-onu-type {
          type identityref {
            base bbf-vomcit:xpon-onu-type;
          }
          description
            "The ONU's xPON type.";
        }
        action delete-onu {
          description
            "Delete an ONU within the ONU Proxy. Note that this is not
             the YANG state data but the Managed Entities state data
             used to manage the ONU (e.g., MIB data sync valule).";
          input {
            leaf delete-state-data {
              type boolean;
              default "true";
              description
                "When true, the ONU state data is deleted.";
            }
          }
        }
        action delete-only-onu-state-data {
          description
            "Delete remaining state data for ONUs that have already
             been deleted from the list of managed ONUS. Note - Do not
             execute this unless the ONU has already been deleted with
             'delete-onu' and with the 'delete-state-data' leaf set to
             'true'. Note that this is not the YANG state data but the
             Managed Entities state data used to manage the ONU (e.g.,
             MIB data sync valule).";
        }
        action set-onu-communication {
          description
            "Dynamically configure the information necessary to
             establish if an ONU can be communicated with by the vOMCI
             Proxy along with remote endpoint to use.";
          input {
            leaf onu-communication-available {
              type boolean;
              description
                "When true, the ONU is able to be communicated with
                 across the ONU management chain of entities.";
            }
            leaf olt-remote-endpoint {
              type bbf-yang:string-ascii64;
              description
                "The remote endpoint name to use for transmitting
                 vOMCI messages toward the OLT.";
            }
            leaf vomci-function-remote-endpoint {
              type bbf-yang:string-ascii64;
              description
                "The remote endpoint name to use for transmitting
                 vOMCI messages toward the vOMCI function.";
            }
            leaf xpon-onu-type {
              type identityref {
                base bbf-vomcit:xpon-onu-type;
              }
              description
                "The ONU's xPON type.";
            }
            uses bbf-vomci-c:vomci-onu-header;
          }
        }
        uses bbf-vomci-c:vomci-onu-header;
        leaf onu-communication-available {
          type boolean;
          description
            "When true, the ONU is able to be communicated with
             across the ONU management chain of entities.";
        }
        leaf olt-remote-endpoint {
          type bbf-yang:string-ascii64;
          description
            "The name remote endpoint to use for transmitting vOMCI
             messages toward the OLT.";
        }
        leaf vomci-function-remote-endpoint {
          type bbf-yang:string-ascii64;
          description
            "The remote endpoint name to use for transmitting vOMCI
             messages toward the vOMCI function.";
        }
        container statistics {
          description
            "vOMCI message and retransmission statistics.";
          action reset {
            description
              "Reset the counters of the vomci-statistics.";
          }
          uses bbf-vomci-c:vomci-message-statistics;
          uses bbf-omci-mr:omci-message-retransmission-statistics {
            if-feature "bbf-omci-mr:omci-message-retransmission";
          }
        }
      }
    }
  }

  augment "/bbf-vomci-proxy:vomci"
        + "/bbf-vomci-proxy:remote-nf"
        + "/bbf-vomci-proxy:nf-client"
        + "/bbf-vomci-proxy:initiate"
        + "/bbf-vomci-proxy:remote-server" {
    description
      "Augment per endpoint statistics on the remote server.";
    container statistics {
      config false;
      description
        "Statistics associated with the remote server.";
      action reset {
        description
          "Reset the statistics.";
      }
      uses bbf-vomci-c:endpoint-message-statistics;
    }
  }

  augment "/bbf-vomci-proxy:vomci"
        + "/bbf-vomci-proxy:remote-nf"
        + "/bbf-vomci-proxy:nf-server"
        + "/bbf-vomci-proxy:listen"
        + "/bbf-vomci-proxy:listen-endpoint" {
    description
      "Adds per endpoint statistics.";
    container statistics {
      config false;
      description
        "Statistics associated with the local server endpoint.";
      action reset {
        description
          "Reset the statistics.";
      }
      uses bbf-vomci-c:endpoint-message-statistics;
    }
  }
}
