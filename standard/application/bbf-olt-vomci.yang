module bbf-olt-vomci {
  yang-version 1.1;
  namespace "urn:bbf:yang:bbf-olt-vomci";
  prefix bbf-olt-vomci;

  import bbf-network-function-client {
    prefix bbf-nfc;
  }
  import bbf-network-function-server {
    prefix bbf-nfs;
  }
  import bbf-vomci-types {
    prefix bbf-vomcit;
  }
  import bbf-xponvani {
    prefix bbf-xponvani;
  }
  import bbf-yang-types {
    prefix bbf-yang;
  }
  import ietf-interfaces {
    prefix if;
  }
  import bbf-vomci-common {
    prefix bbf-vomci-c;
  }

  organization
    "Broadband Forum <https://www.broadband-forum.org>
     SDN/NFV Work Area";
  contact
    "Comments or questions about this Broadband Forum YANG module
     should be directed to <mailto:help@broadband-forum.org>.

     Editor:      Andre Brizido, Altice Labs

     PS Leader:   Ken Kerpez, DZS

     WA Director: Mengmeng Li, China Mobile

     WA Director: Bruno Cornaglia, Vodafone

     WA Director: Haomian Zheng, Huawei";
  description
    "This module contains a collection of YANG definitions for
     supporting the Broadband Forum requirements for a physical OLT's
     implementation of the vOMCI functionality as described in TR-451.

     Copyright (c) 2019-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451a1; see
     the TR itself for full legal notices.";

  revision 2025-02-03 {
    description
      "Amendment 1.
       * Approval Date:    2025-02-03.
       * Publication Date: 2025-02-03.";
    reference
      "TR-451a1: vOMCI Specification
               <https://www.broadband-forum.org/technical/download/
                        TR-451_Amendment-1.pdf>";
  }
  revision 2022-06-07 {
    description
      "Issue 1.
       * Approval Date:    2022-06-07.
       * Publication Date: 2022-06-07.";
    reference
      "TR-451: vOMCI Specification
               <https://www.broadband-forum.org/technical/download/
                        TR-451_Issue-1.pdf>";
  }

  feature nf-client {
    description
      "Indicates that client connectivity to network function
       endpoints is supported.";
  }

  feature nf-server {
    description
      "Indicates that server connectivity to network function
       endpoints is supported.";
  }

  container remote-nf {
    presence "Enables access to remote network functions.";
    description
      "Data nodes to manage remote network functions (NF).";
    container nf-client {
      if-feature "bbf-olt-vomci:nf-client";
      description
        "Client network function configuration.";
      leaf enabled {
        type boolean;
        default "true";
        description
          "Administratively enable the use of client connectivity
           capability to connect to network function endpoints.";
      }
      uses bbf-nfc:nf-client;
    }
    container nf-server {
      if-feature "bbf-olt-vomci:nf-server";
      description
        "Server network function configuration.";
      leaf enabled {
        type boolean;
        default "true";
        description
          "Administratively enable the use of server connectivity
           capability to connect to network function endpoints.";
      }
      uses bbf-nfs:nf-server;
    }
    container nf-endpoint-filter {
      description
        "The network function endpoint filter.";
      list rule {
        key "name";
        ordered-by user;
        description
          "A rule to identify an endpoint of an ONU.

           A rule contains a classification of resources that match a
           criteria. The result is an endpoint name.

           The rule is applied for a given ONU according to priority,
           then list order as defined by the client for equal
           priorities. Once a match is achieved, the search is
           terminated and the endpoint specified in the rule is
           applied.";
        leaf name {
          type bbf-yang:string-ascii64;
          description
            "The rule name.";
        }
        leaf priority {
          type uint16 {
            range "1..max";
          }
          mandatory true;
          description
            "Indicates the priority for applying the match criteria
             of this rule against the priority of match criteria of
             other rules in this filter.

             The higher the value, the lower the priority, i.e.
             priority 1 is the highest priority.";
        }
        container match-criteria {
          description
            "Match criteria for endpoint filters. Specific match
             criteria shall be provided using augments in a context
             dependent way, e.g. match criteria can be augmented for
             ONUs, or in another context match criteria can be
             augmented for another resource.";
          leaf criteria-type {
            type identityref {
              base bbf-vomcit:onu-endpoint-criteria;
            }
            default "bbf-vomcit:any-onu";
            description
              "Indicates the type of matching criteria.";
          }
          leaf onu-vendor {
            when "../criteria-type = 'bbf-vomcit:onu-vendor'" {
              description
                "Only applicable when the criteria type is
                 'onu-vendor'.";
            }
            type bbf-vomcit:onu-vendor-id;
            mandatory true;
            description
              "ONU vendor as defined in the TC layer ONU-ID.";
          }
        }
        leaf endpoint {
          type bbf-yang:string-ascii64;
          description
            "This is the endpoint to use based on the match criteria.

             When operating as a server the resulting endpoint is a
             value that references the leaf 'local-service-endpoint'
             entry in the 'remote-server' list of the
             'listen-endpoint'. When operating as a client the
             resulting endpoint is a value that references the leaf
             'name' in the client's 'remote-server' list. If
             operating as both a client and server to the same
             remote endpoint which session to use (client or server)
             is unspecified as the information transmitted will reach
             the same remote endpoint.";
        }
      }
    }
  }

  augment "/if:interfaces/if:interface/bbf-xponvani:v-ani" {
    description
      "This augmentation defines the configuration data to support
       vANI's that are managed using vOMCI.";
    container vomci-onu {
      description
        "This container provides the elements used for
         vOMCI configuration.";
      container vomci-function {
        description
          "The attributes of a vomci function.";
        leaf remote-endpoint {
          type bbf-yang:string-ascii64;
          description
            "The remote endpoint name to use for transmitting vOMCI
             messages toward the vOMCI function as requested by the
             user. When configured, the entity takes precedence over
             the configured ONU remote endpoint filters.";
        }
      }
    }
  }

  augment "/bbf-olt-vomci:remote-nf"
        + "/bbf-olt-vomci:nf-client"
        + "/bbf-olt-vomci:initiate"
        + "/bbf-olt-vomci:remote-server" {
    description
      "Augment per endpoint statistics on the remote server.";
    container statistics {
      config false;
      description
        "Statistics associated with the remote server.";
      action reset {
        description
          "Reset the statistics.";
      }
      uses bbf-vomci-c:endpoint-message-statistics;
    }
  }

  augment "/bbf-olt-vomci:remote-nf"
        + "/bbf-olt-vomci:nf-server"
        + "/bbf-olt-vomci:listen"
        + "/bbf-olt-vomci:listen-endpoint" {
    description
      "Adds per endpoint statistics.";
    container statistics {
      config false;
      description
        "Statistics associated with the local server endpoint.";
      action reset {
        description
          "Reset the statistics.";
      }
      uses bbf-vomci-c:endpoint-message-statistics;
    }
  }
}
