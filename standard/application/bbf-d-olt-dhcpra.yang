module bbf-d-olt-dhcpra {
  yang-version 1.1;
  namespace "urn:bbf:yang:bbf-d-olt-dhcpra";
  prefix bbf-d-olt-dhcpra;

  import bbf-d-olt-message-monitor {
    prefix bbf-d-olt-msg-mon;
  }
  import bbf-d-olt-network-function-types {
    prefix bbf-d-olt-nft;
  }
  import bbf-dot1q-types {
    prefix bbf-dot1qt;
  }
  import bbf-grpc-client {
    prefix bbf-grpcc;
  }
  import bbf-grpc-server {
    prefix bbf-grpcs;
  }
  import bbf-l2-dhcpv4-relay-profile-common {
    prefix bbf-l2-d4r-pc;
  }
  import bbf-ldra-profile-common {
    prefix bbf-ldra-pc;
  }
  import bbf-network-function-client {
    prefix bbf-nfc;
  }
  import bbf-network-function-server {
    prefix bbf-nfs;
  }
  import bbf-subscriber-profile-common {
    prefix bbf-subprof-pc;
  }
  import bbf-yang-types {
    prefix bbf-yang;
  }
  import ietf-crypto-types {
    prefix ct;
  }
  import ietf-tcp-client {
    prefix tcpc;
  }
  import ietf-tcp-server {
    prefix tcps;
  }
  import ietf-tls-client {
    prefix tlsc;
  }
  import ietf-tls-server {
    prefix tlss;
  }
  import ietf-yang-types {
    prefix yang;
  }

  organization
    "Broadband Forum <https://www.broadband-forum.org>
     SDN/NFV Work Area";
  contact
    "Comments or questions about this Broadband Forum YANG module
     should be directed to <mailto:help@broadband-forum.org>.

     Editor:      Andre Brizido, Altice Labs

     Editor:      Antonio Marsico, Reply

     PS Leader:   Haomian Zheng, Huawei

     WA Director: Mengmeng Li, China Mobile

     WA Director: Bruno Cornaglia, Vodafone";
  description
    "This module contains a collection of YANG definitions for
     supporting the Broadband Forum requirements for disaggregation
     of network functions from a physical OLT (pOLT) into a
     disaggregated-OLT instance (D-OLT) as described in WT-477.

     Specifically, this module describes D-OLT DHCP Relay Agent
     functionality.

     Copyright (c) 2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-477; see
     the TR itself for full legal notices.";

  revision 2024-01-19 {
    description
      "Issue 1.
       * Approval Date:    2024-01-19.
       * Publication Date: 2024-01-19.";
    reference
      "TR-477: Cloud CO Enhancement - Access Node Functional
               Disaggregation <https://www.broadband-forum.org/
                               technical/download/TR-477.pdf>";
  }

  feature d-olt-ldra {
    description
      "Indicates that D-OLT Lightweight DHCPv6 Relay Agent (LDRA)
       is supported.";
    reference
      "TR-177 - IPv6 in the context of TR-101";
  }

  feature d-olt-replace-option-82 {
    description
      "Indicates support for accepting DHCPv4 messages that contain
       option 82 and forwarding the message after having replaced the
       option 82 with a new one generated by the device itself.";
  }

  feature tcp-client-username-password {
    description
      "Indicates that the client supports authenticating using
       username/password when initiating TCP connections.";
  }

  feature tcp-server-username-password {
    description
      "Indicates that the server supports authenticating using
       username/password when receiving TCP connections.";
  }

  container d-olt-dhcpra {
    description
      "The function-specific configuration and data for DHCPRA and
       LDRA.";
    uses bbf-l2-d4r-pc:l2-dhcpv4-relay-profiles;
    uses bbf-ldra-pc:dhcpv6-ldra-profiles;
    container devices {
      description
        "pOLTs, DPUs, or other devices using this D-OLT DHCPRA.
         Note that a pOLT using this D-OLT DHCPRA will not need
         to duplicate this same profile data on the pOLT itself.
         The data configured here is used to create the Agent
         Circuit ID and Remote ID as described in TR-101 and
         TR-156.

         Note that the sum of the information configured in the
         profiles and conveyed via the SCi protobufs comprise the
         total information needed to meet the requirements of
         TR-101 and TR-156 as referenced.";
      reference
        "TR-101 Issue 2, Section 3.9.3
         TR-156 Issue 4, Section 5.7";
      list device {
        key "name";
        description
          "pOLT, DPU, or other device using this D-OLT DHCPRA.";
        leaf name {
          type bbf-yang:string-ascii64;
          description
            "The unique name of the device.";
        }
        leaf access-node-id {
          type bbf-yang:string-ascii64;
          description
            "An identifier representing the Access Node. This string
             will be inserted in case the keyword Access_Node_ID is
             part of the syntax according to which a subscriber
             identification string shall be generated.";
        }
        uses bbf-subprof-pc:subscriber-profiles;
        container vlan-sub-interfaces {
          description
            "The VLAN sub-interfaces (VSIs) on this device
             utilizing this D-OLT DHCPRA.";
          list vsi {
            key "name";
            description
              "A VLAN sub-interface.";
            leaf name {
              type bbf-yang:string-ascii64;
              description
                "The unique name of the VSI.";
            }
            leaf subscriber-profile {
              type leafref {
                path "../../../subscriber-profiles/"
                   + "subscriber-profile/name";
              }
              description
                "A subscriber profile on this D-OLT DHCPRA.";
            }
            leaf l2-dhcpv4-relay-profile {
              type leafref {
                path "../../../../../l2-dhcpv4-relay-profiles/"
                   + "l2-dhcpv4-relay-profile/name";
              }
              description
                "A DHCP profile on this D-OLT DHCPRA.";
            }
            leaf dhcpv6-ldra-profile {
              if-feature "d-olt-ldra";
              type leafref {
                path "../../../../../dhcpv6-ldra-profiles/"
                   + "dhcpv6-ldra-profile/name";
              }
              description
                "A LDRA profile on this D-OLT DHCPRA.";
            }
            leaf trusted-port {
              type union {
                type boolean;
                type enumeration {
                  enum replace {
                    if-feature "d-olt-replace-option-82";
                    description
                      "For DHCPv4 messages containing option 82
                       information, remove the existing option 82
                       information and replace it based on the
                       additional configuration for the L2 DHCPv4
                       Relay Agent.";
                  }
                }
              }
              default "false";
              description
                "Affects the processing of DHCPv4 messages received
                 on the interface that contain option 82, and DHCPv6
                 messages received on the interface.

                 The value 'true' means messages containing option
                 82 are accepted and forwarded with option 82
                 unchanged. When the L2 DHCP Relay Agent receives in
                 the downstream direction a reply containing option
                 82, which is a copy of the value that was passed in
                 the upstream direction, then it does not remove
                 this and sends the message on the interface with
                 option 82 kept in.

                 The value 'false' means the DHCPv4 messages
                 containing option 82 shall be discarded.

                 The value 'replace' means that the DHCPv4 message
                 received on the interface will be modified before
                 forwarding the message. The option 82 that is
                 present in downstream messages, which is a copy of
                 the one generated by the L2 DHCPv4 Relay Agent,
                 shall be removed before sending the message on the
                 interface.

                 Does not affect the processing of DHCPv4 messages
                 received on the interface without option 82.

                 When a client-facing interface is marked as trusted
                 for the LDRA. When a client-facing interface is
                 deemed untrusted, i.e., configured 'false', then
                 the LDRA MUST discard any message of type
                 RELAY-FORW (12) received from the client-facing
                 interface. When an interface is trusted i.e.,
                 configured 'true', then the RELAY-FORW DHCPv6
                 message coming from an LDRA, or other messages
                 coming from a client such as a Solicit message, are
                 forwarded embedded in a new RELAY-FORW message.";
            }
            container vlans {
              description
                "Optional VLAN information that can be used to
                 generate a subscriber identification string.";
              reference
                "TR-101 Issue 2, Table 2
                 TR-156 Issue 4, Table 1";
              leaf c-vid-on-u {
                type bbf-dot1qt:vlan-id;
                description
                  "Q or C VLAN ID on the U interface. This value will
                   be inserted in case the keyword Q-VID is part of
                   the syntax according to which subscriber
                   identification string shall be generated.";
                reference
                  "TR-101 Issue 2, Table 2
                   TR-156 Issue 4, Table 1";
              }
              leaf c-vid-on-v {
                type bbf-dot1qt:vlan-id;
                description
                  "C VLAN ID on the V interface. This value will be
                   inserted in case the keyword C-VID is part of the
                   syntax according to which subscriber
                   identification string shall be generated.";
                reference
                  "TR-101 Issue 2, Table 2";
              }
              leaf s-vid-on-v {
                type bbf-dot1qt:vlan-id;
                description
                  "S VLAN ID on the V interface. This value will be
                   inserted in case the keyword S-VID is part of the
                   syntax according to which subscriber
                   identification string shall be generated.";
                reference
                  "TR-101 Issue 2, Table 2";
              }
              leaf p-bit-on-v {
                type bbf-dot1qt:pbit;
                description
                  "Ethernet Priority bits on the V interface. This
                   value will be inserted in case the keyword
                   'Ethernet Priority' is part of the syntax
                   according to which subscriber identification
                   string shall be generated.";
                reference
                  "TR-101 Issue 2, Section 3.9.3, Table 2
                   TR-156 Issue 4, Section 5.7, Table 1";
              }
            }
            container dhcrpa-statistics {
              presence "DHCPRA functionality is enabled and DHCPRA
                        statistics are available.";
              config false;
              description
                "The message statistics related to the L2 DHCPv4
                  Relay Agent.";
              leaf in-bad-messages-from-client {
                type yang:counter32;
                units "messages";
                description
                  "Bad DHCPv4 messages received on the interface.
                   The messages are received from a DHCPv4 Client
                   connected to it (directly or indirectly through
                   a network).

                   Discontinuities in the counter can occur at
                   re-initialization of the management system,
                   and/or when the L2 DHCPv4 Relay Agent
                   functionality is disabled/enabled.";
              }
              leaf in-bad-messages-from-server {
                type yang:counter32;
                units "messages";
                description
                  "Bad DHCPv4 messages received on the interface.
                   The messages are received from a DHCPv4 Server
                   connected to it (directly or indirectly through a
                   network).

                   Discontinuities in the counter can occur at
                   re-initialization of the management system,
                   and/or when the L2 DHCPv4 Relay Agent
                   functionality is disabled/enabled.";
              }
              leaf in-messages-from-client {
                type yang:counter32;
                units "messages";
                description
                  "Valid DHCPv4 messages received on the interface.
                   The messages are received from a DHCPv4 Client
                   connected to it (directly or indirectly through a
                   network).

                   Discontinuities in the counter can occur at
                   re-initialization of the management system,
                   and/or when the L2 DHCPv4 Relay Agent
                   functionality is disabled/enabled.";
              }
              leaf in-messages-from-server {
                type yang:counter32;
                units "messages";
                description
                  "Valid DHCPv4 messages received on the interface.
                   The messages are received from a DHCPv4 Server
                   connected to it (directly or indirectly through a
                   network).

                   Discontinuities in the counter can occur at
                   re-initialization of the management system,
                   and/or when the L2 DHCPv4 Relay Agent
                   functionality is disabled/enabled.";
              }
              leaf out-messages-to-server {
                type yang:counter32;
                units "messages";
                description
                  "Valid DHCPv4 messages sent to the interface. The
                   messages are sent to a DHCPv4 Server connected to
                   it (directly or indirectly through a network).

                   Discontinuities in the counter can occur at
                   re-initialization of the management system,
                   and/or when the L2 DHCPv4 Relay Agent
                   functionality is disabled/enabled.";
              }
              leaf out-messages-to-client {
                type yang:counter32;
                units "messages";
                description
                  "Valid DHCPv4 messages sent to the interface. The
                   messages are sent to a DHCPv4 Client connected to
                   it (directly or indirectly through a network).

                   Discontinuities in the counter can occur at
                   re-initialization of the management system,
                   and/or when  L2 DHCPv4 Relay Agent functionality
                   is disabled/enabled.";
              }
              leaf option-82-inserted-messages-to-server {
                type yang:counter32;
                units "messages";
                description
                  "DHCPv4 messages from a Client to a Server that
                   pass this interface and into which the L2 DHCPv4
                   Relay inserted option 82.

                   Discontinuities in the counter can occur at
                   re-initialization of the management system,
                   and/or when the L2 DHCPv4 Relay Agent
                   functionality is disabled/enabled.";
              }
              leaf option-82-removed-messages-to-client {
                type yang:counter32;
                units "messages";
                description
                  "DHCPv4 messages from a Server to a Client that
                   pass this interface and from which the L2 DHCPv4
                   Relay removed option 82.

                   Discontinuities in the counter can occur at
                   re-initialization of the management system,
                   and/or when the L2 DHCPv4 Relay Agent
                   functionality is disabled/enabled.";
              }
              leaf option-82-not-inserted-to-server {
                type yang:counter32;
                units "messages";
                description
                  "DHCPv4 messages from a Client to a Server that
                   pass this interface and for which the L2 DHCPv4
                   Relay did not insert option 82 because after
                   insertion the length would exceed the maximum
                   allowed packet size.

                   Discontinuities in the counter can occur at
                   re-initialization of the management system,
                   and/or when the L2 DHCPv4 Relay Agent
                   functionality is disabled/enabled.";
              }
              action reset {
                description
                  "Reset the statistics.";
              }
            }
            container ldra-statistics {
              if-feature "d-olt-ldra";
              presence "LDRA functionality is enabled and LDRA
                        statistics are available.";
              config false;
              description
                "The message statistics related to the Lightweight
                 DHCPv6 Relay Agent.";
              leaf in-bad-messages-from-client {
                type yang:counter32;
                units "messages";
                description
                  "Bad DHCPv6 messages received on the interface.
                   The messages are received from a DHCPv6 Client
                   connected to it (directly or indirectly through a
                   network).

                   Discontinuities in the counter can occur at
                   re-initialization of the management system,
                   and/or when the LDRA functionality is
                   disabled/enabled.";
              }
              leaf in-bad-messages-from-server {
                type yang:counter32;
                units "messages";
                description
                  "Bad DHCPv6 messages received on the interface.
                   The messages are received from a DHCPv6 Server
                   connected to it (directly or indirectly through a
                   network).

                   Discontinuities in the counter can occur at
                   re-initialization of the management system,
                   and/or when the LDRA functionality is
                   disabled/enabled.";
              }
              leaf option-17-inserted-messages-to-server {
                type yang:counter32;
                units "messages";
                description
                  "DHCPv6 messages from a Client to a Server that
                   passed this interface and for which the LDRA did
                   insert option 17.

                   Discontinuities in the counter can occur at
                   re-initialization of the management system,
                   and/or when the LDRA functionality is
                   disabled/enabled.";
              }
              leaf option-17-removed-messages-to-client {
                type yang:counter32;
                units "messages";
                description
                  "DHCPv6 messages from a Server to a Client that
                   passed this interface and for which the LDRA did
                   remove option 17.

                   Discontinuities in the counter can occur at
                   re-initialization of the management system,
                   and/or when the LDRA functionality is
                   disabled/enabled.";
              }
              leaf option-18-inserted-messages-to-server {
                type yang:counter32;
                units "messages";
                description
                  "DHCPv6 messages from a Client to a Server that
                   passed this interface and for which the LDRA did
                   insert option 18.

                   Discontinuities in the counter can occur at
                   re-initialization of the management system,
                   and/or when the LDRA functionality is
                   disabled/enabled.";
              }
              leaf option-18-removed-messages-to-client {
                type yang:counter32;
                units "messages";
                description
                  "DHCPv6 messages from a Server to a Client that
                   passed this interface and for which the LDRA did
                   remove option 18.

                   Discontinuities in the counter can occur at
                   re-initialization of the management system,
                   and/or when the LDRA functionality is
                   disabled/enabled.";
              }
              leaf option-37-inserted-messages-to-server {
                type yang:counter32;
                units "messages";
                description
                  "DHCPv6 messages from a Client to a Server that
                   passed this interface and for which the LDRA did
                   insert option 37.

                   Discontinuities in the counter can occur at
                   re-initialization of the management system,
                   and/or when the LDRA functionality is
                   disabled/enabled.";
              }
              leaf option-37-removed-messages-to-client {
                type yang:counter32;
                units "messages";
                description
                  "DHCPv6 messages from a Server to a Client that
                   passed this interface and for which the LDRA did
                   remove option 37.

                   Discontinuities in the counter can occur at
                   re-initialization of the management system,
                   and/or when the LDRA functionality is
                   disabled/enabled.";
              }
              leaf outgoing-mtu-exceeded-messages-from-client {
                type yang:counter32;
                units "messages";
                description
                  "DHCPv6 messages from a Client that are dropped
                   because the Relay-Message size after adding the
                   options would exceed the MTU of the outgoing
                   interface.

                   Discontinuities in the counter can occur at
                   re-initialization of the management system,
                   and/or when the LDRA functionality is
                   disabled/enabled.";
                reference
                  "RFC 6221 - Section 5.3.1";
              }
              action reset {
                description
                  "Reset the statistics.";
              }
            }
          }
        }
      }
    }
    container remote-nf {
      presence "Enables access to remote network functions";
      description
        "Remote network function (NF) configuration.";
      container nf-client {
        description
          "Client network function configuration.";
        leaf enabled {
          type boolean;
          default "true";
          description
            "Administratively enable the use of client connectivity
             capability to connect to network function endpoints.";
        }
        uses bbf-nfc:nf-client {
          augment "initiate/remote-server" {
            description
              "Augment the client network function remote server with
               the type of Management Flow Control (Mfc) interface to
               use";
            leaf mfc-type {
              type identityref {
                base bbf-d-olt-nft:d-olt-mfc;
              }
              description
                "Type of Mfc.";
            }
          }
          augment "initiate/remote-server/transport" {
            description
              "Augment the client network function remote
               server transport choice with an option for gRPC.";
            case grpc {
              description
                "Selection for gRPC client transport.";
              uses bbf-grpcc:grpc-client-transport {
                augment
                  "grpc-client/access-point/"
                + "grpc-transport-parameters/tcp-client-options" {
                  description
                    "The gRPC client can use TCP and optional TLS.";
                  case tcp-or-tls-transport {
                    description
                      "Select TCP and optional TLS transport.";
                    container tcp-client-parameters {
                      description
                        "The TCP configuration.";
                      uses tcpc:tcp-client-grouping;
                      choice auth-type {
                        description
                          "A choice among supported authentication
                           mechanisms.";
                        case username-password {
                          if-feature "tcp-client-username-password";
                          container username-password {
                            leaf username {
                              type string;
                              mandatory true;
                              description
                                "The 'username' value to use for
                                 client identification.";
                            }
                            uses ct:password-grouping {
                              description
                                "The password to be used for client
                                 authentication.";
                            }
                            description
                              "The username/password configuration.
                               configuration.";
                          }
                        }
                      }
                    }
                    container tls-client-parameters {
                      presence "Indicates usage of optional TLS.";
                      description
                        "The TLS configuration.";
                      uses tlsc:tls-client-grouping;
                    }
                  }
                }
              }
            }
          }
          augment "initiate/remote-server" {
            description
              "Statistics for Mfc-SCi or Mfc-CPRi.";
            container mfc-statistics {
              config false;
              description
                "Statistics for Mfc-SCi or Mfc-CPRi.";
              action reset {
                description
                  "Reset the statistics.";
              }
              uses bbf-d-olt-msg-mon:d-olt-message-statistics;
            }
          }
        }
      }
      container nf-server {
        description
          "Server network function configuration.";
        leaf enabled {
          type boolean;
          default "true";
          description
            "Administratively enable the use of server connectivity
             capability to connect from network function
             endpoints.";
        }
        uses bbf-nfs:nf-server {
          augment "listen/listen-endpoint" {
            description
              "Augment the server network function listen endpoint
               with the type of Management Flow Control (Mfc)
               interface to use.";
            leaf mfc-type {
              type identityref {
                base bbf-d-olt-nft:d-olt-mfc;
              }
              description
                "Type of Mfc.";
            }
          }
          augment "listen/listen-endpoint/transport" {
            description
              "Augment the server network function listen endpoint
               choice with an option for gRPC.";
            case grpc {
              description
                "Selection for gRPC client transport.";
              uses bbf-grpcs:grpc-server-transport {
                augment "grpc-server/tcp-client-options" {
                  description
                    "The gRPC server can use TCP and optional TLS.";
                  case tcp-or-tls-transport {
                    description
                      "Select TCP and optional TLS transport.";
                    container tcp-server-parameters {
                      description
                        "The TCP configuration.";
                      uses tcps:tcp-server-grouping;
                      choice auth-type {
                        description
                          "A choice among supported authentication
                           mechanisms.";
                        case username-password {
                          if-feature "tcp-server-username-password";
                          container username-password {
                            leaf username {
                              type string;
                              mandatory true;
                              description
                                "The 'username' value to permit for
                                 client identification.";
                            }
                            uses ct:password-grouping {
                              description
                                "The password to permit for client
                                 authentication.";
                            }
                            description
                              "The Username/Password
                               configuration.";
                          }
                        }
                      }
                    }
                    container tls-server-parameters {
                      presence "Indicates usage of optional TLS.";
                      description
                        "The optional TLS configuration.";
                      uses tlss:tls-server-grouping;
                    }
                  }
                }
              }
            }
          }
          augment "listen/listen-endpoint" {
            description
              "Statistics for Mfc-SCi or Mfc-CPRi.";
            container mfc-statistics {
              config false;
              description
                "Statistics for Mfc-SCi or Mfc-CPRi.";
              action reset {
                description
                  "Reset the statistics.";
              }
              uses bbf-d-olt-msg-mon:d-olt-message-statistics;
            }
          }
        }
      }
    }
  }
}
