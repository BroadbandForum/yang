module bbf-d-olt-vdba {
  yang-version 1.1;
  namespace "urn:bbf:yang:bbf-d-olt-vdba";
  prefix bbf-d-olt-vdba;

  import bbf-yang-types {
    prefix bbf-yang;
  }
  import ietf-yang-types {
    prefix yang;
  }
  import bbf-xpongemtcont {
    prefix bbf-xpongemtcont;
  }

  organization
    "Broadband Forum <https://www.broadband-forum.org>
     Provider Cloud Work Area";
  contact
    "Comments or questions about this Broadband Forum YANG module
     should be directed to <mailto:info@broadband-forum.org>.

     Editor:      Huseyin Ahmet Aydin, Vodafone

     Editor:      Antonio Marsico, Reply

     PS Leader:   Sven Ooghe, Nokia

     PS Leader:   Joey Boyd, Adtran

     WA Director: Bruno Cornaglia, Vodafone

     WA Director: Aihua Guo, Futurewei";
  description
    "This module contains a collection of YANG definitions for
     supporting the Broadband Forum requirements for disaggregation
     of network functions from a physical OLT into a disaggregated-
     OLT instance (d-OLT) as described in TR-477. Specifically, this
     module defines d-OLT virtual Dynamic Bandwidth Allocation
     (vDBA).

     Copyright (c) 2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-403a1; see
     the TR itself for full legal notices.";

  revision 2026-03-04 {
    description
      "Amendment 1.
       * Approval Date:    2026-03-04.
       * Publication Date: 2026-03-04.";
    reference
      "TR-403a1: PON Abstraction Interface Specifications
                 <https://www.broadband-forum.org/technical/download/
                          TR-403_Amendment-1.pdf>";
  }

  container vdba {
    presence "Enables vDBA functionality.";
    description
      "vDBA configuration.";
    reference
      "TR-402;
       TR-403";
    leaf bandwidth-threshold {
      type union {
        type enumeration {
          enum disabled {
            description
              "Bandwidth threshold checking is disabled.";
          }
        }
        type uint32 {
          range "1..max";
        }
      }
      units "kilobits per second";
      description
        "Bandwidth threshold for vDBA. A value of 'disabled'
         disables threshold checking.";
    }
    container operational-state {
      config false;
      description
        "Operational state data.";
      leaf bandwidth-usage {
        type uint32;
        units "kilobits per second";
        description
          "Current bandwidth usage in kbps.";
      }
      leaf allocation-efficiency {
        type uint8 {
          range "0..100";
        }
        units "percent";
        description
          "Efficiency of bandwidth allocation as a percentage.
           Calculated as (actually used bandwidth / total allocated
           bandwidth to ONUs) x 100. This is independent of the
           bandwidth-threshold value.";
      }
    }
    list device {
      key "name";
      description
        "pOLT, DPU, or other device using this D-OLT-vDBA.";
      leaf name {
        type bbf-yang:string-ascii64;
        description
          "The unique name of the device.";
      }
      container interfaces {
        description
          "The PON interfaces on this device utilizing this
           D-OLT-vDBA.";
        list interface {
          key "name";
          description
            "A PON port.";
          leaf name {
            type bbf-yang:string-ascii64;
            description
              "The unique name of the PON port.";
          }
          leaf engine-number {
            type uint8;
            description
              "Designates which engine to call this API from the
               application (algorithm) perspective.";
          }
        }
      }
    }
  }

  rpc set-grant {
    description
      "Set dynamic grant allocation parameters for a specific PON port
       as defined in WT-403 Table 2.";
    reference
      "WT-403 Section 4.2.1";
    input {
      leaf engine-number {
        type uint8;
        description
          "From the viewpoint of application (algorithm),
           designates which engine to call this API.";
      }
      leaf pon-id {
        type uint8;
        description
          "Designates the target logical PON port.";
      }
      leaf dba-cycle-number {
        type uint32;
        description
          "DBA is processed on cycle basis. Indicates the timeline
           of the allocation. Expected to increment from previous
           DBA cycle with possible wrap-around.";
      }
      leaf list-size {
        type uint32;
        description
          "Number of elements in the grant list.";
      }
      leaf alloc-id {
        type bbf-xpongemtcont:alloc-id;
        description
          "Target Transmission Container (T-CONT) Allocation
           Identifier (Alloc-ID).";
        reference
          "ITU-T G.984.3 Clause 5.5.3;
           ITU-T G.987.3 Clause 6.4.3;
           ITU-T G.9807.1 Clause C.6.1.5.7;
           ITU-T G.989.3 Clause 6.1.5.7;
           ITU-T G.9804.2 Clause 6.5.2.6;
           MSA 25GS-PON Section C.6.1.5.7";
      }
      leaf allocation-size {
        type uint16;
        description
          "GrantSize field. The unit is 4-byte blocks for
           2.48832 Gbps and 16-byte blocks for 9.95328 Gbps.";
        reference
          "ITU-T G.989.3 Clause 8.1.1.2.4";
      }
      leaf start-time {
        type uint16;
        description
          "StartTime field. The unit is 4-byte blocks for
           2.48832 Gbps and 16-byte blocks for 9.95328 Gbps.";
        reference
          "ITU-T G.989.3 Clause 8.1.1.2.3";
      }
      leaf burst-profile {
        type uint8 {
          range "0..3";
        }
        description
          "Burst profile for upstream, used in constructing BWmap.";
        reference
          "ITU-T G.989.3 Clause 8.1.1.2.6";
      }
      leaf fwi {
        type boolean;
        description
          "Forced Wake-up Indication. Notifies the ONU to wake up
           during the ONU power management process.";
        reference
          "ITU-T G.989.3 Clause 8.1.1.2.5;
           ITU-T G.984.3;
           ITU-T G.9807.1";
      }
      leaf end-of-map {
        type boolean;
        description
          "Indicates this element is the last one in the API call.";
      }
      leaf end-of-frame {
        type boolean;
        description
          "Indicates this element is the last one in the 125
           microsecond BWmap.";
      }
      leaf dbru-flag {
        type boolean;
        description
          "Dynamic Bandwidth Report upstream flag.";
        reference
          "ITU-T G.989.3 Clause 8.1.1.2.2;
           ITU-T G.984.3;
           ITU-T G.9807.1";
      }
      leaf ploamu-flag {
        type boolean;
        description
          "Physical Layer OAM upstream flag.";
        reference
          "ITU-T G.989.3 Clause 8.1.1.2.2;
           ITU-T G.984.3;
           ITU-T G.9807.1";
      }
    }
    output {
      leaf result {
        type enumeration {
          enum successful {
            description
              "Grant allocation was successful.";
          }
          enum failed {
            description
              "Grant allocation failed.";
          }
          enum invalid-parameters {
            description
              "Invalid input parameters provided.";
          }
        }
        description
          "Result of the RPC execution.";
      }
    }
  }

  rpc get-report {
    description
      "Get the status report from the engine as defined
       in WT-403 Table 3.";
    reference
      "WT-403 Section 4.2.2";
    output {
      leaf pon-id {
        type uint8;
        description
          "Source logical PON port of the status report.";
      }
      leaf dba-cycle-number {
        type uint32;
        description
          "DBA cycle timeline indicator. Expected to increment
           from previous DBA cycle.";
      }
      leaf sfc {
        type uint64;
        description
          "Super Frame Counter indicating timeline of allocation.
           Represents the first frame of the DBA cycle.";
      }
      leaf available-bw-blocks {
        type uint32;
        description
          "Available bandwidth blocks for all active Alloc-IDs.";
      }
      leaf number-of-alloc-ids {
        type uint16;
        description
          "Number of Alloc-IDs included in this callback.";
      }
      leaf number-of-onus {
        type uint16;
        description
          "Number of active ONUs for which PLOAM queue status
           is received in this callback.";
      }
      list alloc-id-report {
        key "alloc-id";
        description
          "Report for each Alloc-ID.";
        leaf alloc-id {
          type bbf-xpongemtcont:alloc-id;
          description
            "Alloc-ID of the status report.";
        }
        leaf allocated-bw-blocks {
          type uint32;
          description
            "Number of bandwidth blocks allocated to this Alloc-ID.";
        }
        leaf used-bw-blocks {
          type uint32;
          description
            "Number of bandwidth blocks actually used by this
             Alloc-ID.";
        }
        leaf buffer-occupancy {
          type uint32;
          description
            "Buffer occupancy (BufOcc) of the Alloc-ID, representing
             the amount of data currently queued in the ONU's upstream
             buffer awaiting transmission.";
          reference
            "ITU-T G.989.3 Clause 8.1.2.2.1;
             ITU-T G.984.3 Clause 8.4.2;
             ITU-T G.9807.1 Clause 8.1.2.2.1;
             RFC 791 Appendix B";
        }
      }
      list onu-report {
        key "onu-id";
        description
          "PLOAM queue status for each ONU.";
        leaf onu-id {
          type uint16;
          description
            "ONU ID of the PLOAM queue status.";
        }
        leaf ploam-queue-status {
          type boolean;
          description
            "If 'true', the ONU's queue of pending upstream PLOAMu
             messages will remain non-empty after the current burst
             is transmitted.

             If 'false', no additional upstream PLOAMu messages are
             awaiting transmission.";
          reference
            "ITU-T G.984.3 Clause 8.2.2.3;
             ITU-T G.9807.1 Clause C.8.1.2.1.2;
             ITU-T G.989.3 Clause 8.1.2.1.2;
             RFC 791 Appendix B";
        }
      }
    }
  }

  notification bandwidth-threshold-crossed {
    description
      "Indicates when bandwidth usage exceeds configured threshold.";
    leaf device-name {
      type string;
      description
        "Name of the affected device.";
    }
    leaf current-usage {
      type uint32;
      units "kilobits per second";
      description
        "Measured bandwidth usage at the time of threshold crossing.";
    }
    leaf bandwidth-threshold {
      type union {
        type enumeration {
          enum disabled {
            description
              "Bandwidth threshold checking is disabled.";
          }
        }
        type uint32 {
          range "1..max";
        }
      }
      units "kilobits per second";
      description
        "The threshold configuration that was in effect when the
         event occurred.";
    }
    leaf timestamp {
      type yang:date-and-time;
      description
        "Time when the threshold was crossed.";
    }
  }
}
