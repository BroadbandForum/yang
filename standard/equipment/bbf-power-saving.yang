module bbf-power-saving {
  yang-version 1.1;
  namespace "urn:bbf:yang:bbf-power-saving";
  prefix bbf-pwr-sav;

  import ietf-hardware {
    prefix hw;
  }

  organization
    "Broadband Forum <https://www.broadband-forum.org>
     Provider Cloud Work Area";
  contact
    "Comments or questions about this Broadband Forum YANG module
     should be directed to <mailto:info@broadband-forum.org>.

     Editor:      Shiya Ashraf, Nokia

     PS Leader:   Sven Ooghe, Nokia

     PS Leader:   Joey Boyd, Adtran

     WA Director: Bruno Cornaglia, Vodafone

     WA Director: Aihua Guo, Futurewei";
  description
    "This module contains a collection of YANG definitions for
     supporting the Broadband Forum requirements for managing access
     network equipment (e.g., BBF-specified Access Nodes and FTTdp
     DPUs).

     Specifically, this module models data containers to manage power
     saving. The intent of these containers is to be augmented by
     device type-specific power saving data nodes.

     Copyright (c) 2017-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a11; see
     the TR itself for full legal notices.";

  revision 2026-10-19 {
    description
      "Amendment 11.
       * Approval Date:    2026-10-19.
       * Publication Date: 2026-10-19.";
    reference
      "TR-383a11: Common YANG Modules for Access Networks
                  <https://www.broadband-forum.org/technical/download/
                           TR-383_Amendment-11.pdf>";
  }

  container power-saving {
    description
      "System level configuration to control power saving.

       This can be further augmented with configuration specific
       to domains where power saving can be achieved.";
  }

  augment "/hw:hardware/hw:component" {
    description
      "Augments a specific hardware component with a power saving
       container.";
    container power-saving {
      presence "Enable power saving for this hardware component.";
      description
        "Data that defines the power saving behavior of the hardware
         component. The data configured at this level overrides global
         power saving setting made for this hardware class, if any.";
      container state {
        config false;
        description
          "Power saving state data for the hardware component.";
      }
    }
  }
}
