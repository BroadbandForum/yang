module bbf-hardware-types {
  yang-version 1.1;
  namespace "urn:bbf:yang:bbf-hardware-types";
  prefix bbf-hwt;

  import iana-hardware {
    prefix ianahw;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on reusable data
     types as applicable to access network equipment. As such, this
     module is specific to access network equipment (e.g.,
     BBF-specified Access Nodes and FTTdp DPUs).

     Specifically, this module specializes types defined in the
     iana-hardware model.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2019-06-11 {
    description
      "Amendment 2.
       * Approval Date:    2019-06-11
       * Publication Date: 2019-06-11.";
    reference
      "TR-355a2: YANG Modules for FTTdp Management
                 <https://www.broadband-forum.org/technical/download/
                        TR-355_Amendment-2.pdf>";
  }
  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }

  feature fastdsl-nt {
    description
      "Indicates whether the device supports management of Network
       Terminations (NT) connected to its FAST or DSL Lines as a
       remote hardware component within the device's Hardware
       Management YANG data model.";
  }

  feature xpon-nt {
    description
      "Indicates whether the device supports management of Network
       Terminations (NT) connected to its xPON interfaces as a
       remote hardware component within the device's hardware
       Management YANG data model.";
  }

  identity slot {
    base ianahw:container;
    description
      "A 'slot' is a special type of container that can contain a
       pluggable board.";
  }

  identity cage {
    base ianahw:container;
    description
      "A 'cage' is a special type of container that can contain a
       pluggable transceiver.";
  }

  identity board {
    base ianahw:module;
    description
      "A 'board' is a special type of module that represents a
       physical item, commonly known as a board or a card.";
  }

  identity transceiver {
    base ianahw:module;
    description
      "A 'transceiver' is a special type of module that represents a
       physical item like a pluggable SFP, an SFP+, or an XFP; or a
       soldered SFF.";
  }

  identity transceiver-link {
    base ianahw:port;
    description
      "A 'transceiver-link' is a special type of port that terminates
       an optical signal.";
  }

  identity rj45 {
    base ianahw:port;
    description
      "A 'rj45' is a special type of port that terminates an
       electrical Ethernet link.";
  }

  identity fastdsl-tp {
    base ianahw:port;
    description
      "A 'fastdsl-tp' is a special type of port that terminates a
       copper twisted pair supporting a FAST or one of the DSL types
       of link.";
  }

  identity fastdsl-coax {
    base ianahw:port;
    description
      "A 'fastdsl-coax' is a special type of port that terminates a
       coax supporting a FAST or one of the DSL types of link.";
  }

  identity cpu-core {
    base ianahw:cpu;
    description
      "A 'cpu-core' refers to the CPU's core (when multiple cores are
       supported).";
  }

  identity remote-hardware {
    base ianahw:chassis;
    description
      "A 'remote-hardware' is an abstract identity representing
       separate hardware that is not physically part of device's own
       hardware hierarchy, but reported as a remote hardware component
       within the device's Hardware Management YANG data model.";
  }

  identity remote-nt {
    base bbf-hwt:remote-hardware;
    description
      "A 'remote-nt' is an abstract identity representing a device
       that is a remote hardware component that provides the network
       termination of a line.";
  }

  identity fastdsl-nt {
    if-feature "fastdsl-nt";
    base bbf-hwt:remote-nt;
    description
      "A 'fastdsl-nt' is a remote hardware component that provides the
       network termination of a FAST or DSL line.";
  }

  identity xpon-nt {
    if-feature "xpon-nt";
    base bbf-hwt:remote-nt;
    description
      "A 'xpon-nt' is a remote hardware component that provides the
       network termination of an xPON.";
  }
}
