module bbf-hardware-transceivers {
  yang-version 1.1;
  namespace "urn:bbf:yang:bbf-hardware-transceivers";
  prefix bbf-hw-xcvr;

  import bbf-yang-types {
    prefix bbf-yang;
  }
  import ietf-hardware {
    prefix hw;
  }
  import bbf-hardware-types {
    prefix bbf-hwt;
  }

  organization
    "Broadband Forum <https://www.broadband-forum.org>
     Provider Cloud Work Area";
  contact
    "Comments or questions about this Broadband Forum YANG module
     should be directed to <mailto:info@broadband-forum.org>.

     Editor:      Shiya Ashraf, Nokia

     PS Leader:   Sven Ooghe, Nokia

     PS Leader:   Joey Boyd, Adtran

     WA Director: Bruno Cornaglia, Vodafone

     WA Director: Aihua Guo, Futurewei";
  description
    "This module contains a collection of YANG definitions for
     supporting the Broadband Forum requirements on hardware
     management as applicable to access network equipment.
     As such, this module is specific to access network equipment
     (e.g., BBF-specified Access Nodes and FTTdp DPUs).

     Specifically, this module augments the ietf-hardware model with
     management of compact transceivers.

     Copyright (c) 2017-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a10; see
     the TR itself for full legal notices.";

  revision 2026-07-02 {
    description
      "Amendment 10.
       * Approval Date:    2026-07-02.
       * Publication Date: 2026-07-02.";
    reference
      "TR-383a10: Common YANG Modules for Access Networks
                  <https://www.broadband-forum.org/technical/download/
                           TR-383_Amendment-10.pdf>";
  }
  revision 2025-07-02 {
    description
      "Amendment 9.
       * Approval Date:    2025-07-02.
       * Publication Date: 2025-07-02.";
    reference
      "TR-383a9: Common YANG Modules for Access Networks
                 <https://www.broadband-forum.org/technical/download/
                          TR-383_Amendment-9.pdf>";
  }
  revision 2024-11-11 {
    description
      "Amendment 8.
       * Approval Date:    2024-11-11.
       * Publication Date: 2024-11-11.";
    reference
      "TR-383a8: Common YANG Modules for Access Networks
                 <https://www.broadband-forum.org/technical/download/
                          TR-383_Amendment-8.pdf>";
  }
  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }
  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }

  feature vendor-eeprom {
    description
      "Indicates support for reporting the contents of the vendor-
       specific EEPROM data fields.";
    reference
      "SFF-8472 (Revision 12.4) Table 4-1 - Address A0h, Bytes 96-127;
       SFF-8436 (Revision 4.9) Table 29 - Page 00h, Bytes 224-255;
       INF-8077i (Revision 4.5) Table 46 - Page 01h, Bytes 224-255";
  }

  feature vendor-eeprom-string {
    if-feature "vendor-eeprom";
    description
      "Indicates support for reporting the contents of the vendor-
       specific EEPROM data fields as a string.";
    reference
      "SFF-8472 (Revision 12.4) Table 4-1 - Address A0h, Bytes 96-127;
       SFF-8436 (Revision 4.9) Table 29 - Page 00h, Bytes 224-255;
       INF-8077i (Revision 4.5) Table 46 - Page 01h, Bytes 224-255";
  }

  feature vendor-eeprom-binary {
    if-feature "vendor-eeprom";
    description
      "Indicates support for reporting the contents of the vendor-
       specific EEPROM data fields in binary format.";
    reference
      "SFF-8472 (Revision 12.4) Table 4-1 - Address A0h, Bytes 96-127;
       SFF-8436 (Revision 4.9) Table 29 - Page 00h, Bytes 224-255;
       INF-8077i (Revision 4.5) Table 46 - Page 01h, Bytes 224-255";
  }

  feature extended-information {
    description
      "Indicates whether reporting extended information data fields
       of the transceiver are supported.";
    reference
      "SFF-8472 (Revision 12.4) Section 10";
  }

  feature user-eeprom {
    if-feature "extended-information";
    description
      "Indicates support for reporting the contents of the user-
       writable EEPROM data fields.";
    reference
      "SFF-8472 (Revision 12.4) Table 10-4 - Address A2h,
       Page 00h/01h, Bytes 128-247;
       SFF-8436 (Revision 4.9) Section 7.6.4 - Page 02h,
       Bytes 128-255;
       INF-8077i (Revision 4.5) Section 5.45 - Table 02h,
       Bytes 128-255";
  }

  feature user-eeprom-string {
    if-feature "user-eeprom";
    description
      "Indicates support for reporting the contents of the user-
       writable EEPROM data fields as a string.";
    reference
      "SFF-8472 (Revision 12.4) Table 10-4 - Address A2h,
       Page 00h/01h, Bytes 128-247;
       SFF-8436 (Revision 4.9) Section 7.6.4 - Page 02h,
       Bytes 128-255;
       INF-8077i (Revision 4.5) Section 5.45 - Table 02h,
       Bytes 128-255";
  }

  feature user-eeprom-binary {
    if-feature "user-eeprom";
    description
      "Indicates support for reporting the contents of the user-
       writable EEPROM data fields in binary format.";
    reference
      "SFF-8472 (Revision 12.4) Table 10-4 - Address A2h,
       Page 00h/01h, Bytes 128-247;
       SFF-8436 (Revision 4.9) Section 7.6.4 - Page 02h,
       Bytes 128-255;
       INF-8077i (Revision 4.5) Section 5.45 - Table 02h,
       Bytes 128-255";
  }

  feature optical-power-and-sensitivity-in-dbm {
    description
      "Indicates support for reporting optical power and sensitivity
       diagnostic data in dBm.";
  }

  // Alarm/warning flags

  identity transceiver-alarm-warning {
    description
      "Base identity for the basic alarm and warning flags of the
       transceiver.

       This identity is abstract and must not be used for a
       transceiver alarm or warning flag.";
  }

  identity temperature-high {
    base transceiver-alarm-warning;
    description
      "The internal temperature has exceeded the high level
       threshold.";
  }

  identity temperature-low {
    base transceiver-alarm-warning;
    description
      "The internal temperature has dropped below the low level
       threshold.";
  }

  identity supply-voltage-high {
    base transceiver-alarm-warning;
    description
      "The internal supply voltage has exceeded the high level
       threshold.";
  }

  identity supply-voltage-low {
    base transceiver-alarm-warning;
    description
      "The internal supply voltage has dropped below the low level
       threshold.";
  }

  identity link-alarm-warning {
    description
      "Base identity for the physical links of alarm and warning flags
       of the transceiver.

       This identity is abstract and must not be used for a
       transceiver link alarm or warning flag.";
  }

  identity tx-bias-high {
    base link-alarm-warning;
    description
      "The transmit (TX) bias current has exceeded the high level
       threshold.";
  }

  identity tx-bias-low {
    base link-alarm-warning;
    description
      "The transmit (TX) bias current has dropped below the low level
       threshold.";
  }

  identity tx-power-high {
    base link-alarm-warning;
    description
      "The transmit (TX) output power has exceeded the high level
       threshold.";
  }

  identity tx-power-low {
    base link-alarm-warning;
    description
      "The transmit (TX) output power has dropped below the low
       level threshold.";
  }

  identity rx-power-high {
    base link-alarm-warning;
    description
      "The receive (RX) input power has exceeded the high level
       threshold.";
  }

  identity rx-power-low {
    base link-alarm-warning;
    description
      "The receive (RX) input power has dropped below the low level
       threshold.";
  }

  identity laser-temperature-high {
    base link-alarm-warning;
    description
      "The laser temperature has exceeded the high level threshold.";
  }

  identity laser-temperature-low {
    base link-alarm-warning;
    description
      "The laser temperature has dropped below the low level
       threshold.";
  }

  identity tec-current-high {
    base link-alarm-warning;
    description
      "The Thermoelectric Cooler (TEC) current has exceeded the high
       level threshold.";
  }

  identity tec-current-low {
    base link-alarm-warning;
    description
      "The Thermoelectric Cooler (TEC) current has dropped below the
       low level threshold.";
  }

  //Physical Device Identifiers

  identity physical-device {
    description
      "Identifies the physical device.

       This identity is abstract and must not be used to represent a
       physical device.";
    reference
      "SFF-8472 (Revision 12.4) Table 5-1 - Address A0h, Byte 0";
  }

  identity unknown-physical-device {
    base physical-device;
    description
      "Unknown or unspecified.";
    reference
      "SFF-8472 (Revision 12.4) Table 5-1 - Address A0h, Byte 0,
       Value 00h;
       SFF-8024 (Revision 4.12) Table 4-1 - Value 00h";
  }

  identity gbic {
    base physical-device;
    description
      "GBIC.";
    reference
      "SFF-8472 (Revision 12.4) Table 5-1 - Address A0h, Byte 0,
       Value 01h;
       SFF-8024 (Revision 4.12) Table 4-1 - Value 01h";
  }

  identity sff {
    base physical-device;
    description
      "Module/connector soldered to a motherboard (using SFF-8472).";
    reference
      "SFF-8472 (Revision 12.4) Table 5-1 - Address A0h, Byte 0,
       Value 02h;
       SFF-8024 (Revision 4.12) Table 4-1 - Value 02h";
  }

  identity sfp {
    base physical-device;
    description
      "SFP/SFP+/SFP28.";
    reference
      "SFF-8472 (Revision 12.4) Table 5-1 - Address A0h, Byte 0,
       Value 03h;
       SFF-8024 (Revision 4.12) Table 4-1 - Value 03h";
  }

  identity xbi-300-pin {
    base physical-device;
    description
      "300 pin XBI.";
    reference
      "SFF-8024 (Revision 4.12) Table 4-1 - Value 04h";
  }

  identity xenpak {
    base physical-device;
    description
      "XENPAK.";
    reference
      "SFF-8024 (Revision 4.12) Table 4-1 - Value 05h";
  }

  identity xfp {
    base physical-device;
    description
      "XFP.";
    reference
      "SFF-8024 (Revision 4.12) Table 4-1 - Value 06h";
  }

  identity xff {
    base physical-device;
    description
      "XFF.";
    reference
      "SFF-8024 (Revision 4.12) Table 4-1 - Value 07h";
  }

  identity xfp-e {
    base physical-device;
    description
      "XFP-E.";
    reference
      "SFF-8024 (Revision 4.12) Table 4-1 - Value 08h";
  }

  identity xpak {
    base physical-device;
    description
      "XPAK.";
    reference
      "SFF-8024 (Revision 4.12) Table 4-1 - Value 09h";
  }

  identity x2 {
    base physical-device;
    description
      "X2.";
    reference
      "SFF-8024 (Revision 4.12) Table 4-1 - Value 0Ah";
  }

  identity dwdm-sfp {
    base physical-device;
    description
      "DWDM-SFP/SFP+ (not using SFF-8472).";
    reference
      "SFF-8472 (Revision 12.4);
       SFF-8024 (Revision 4.12) Table 4-1 - Value 0Bh";
  }

  identity qsfp {
    base physical-device;
    description
      "QSFP (INF-8438i).";
    reference
      "INF-8438i (Revision 1.0);
       SFF-8024 (Revision 4.12) Table 4-1 - Value 0Ch";
  }

  identity qsfp-plus-or-later {
    base physical-device;
    description
      "QSFP+ or later (SFF-8436, SFF-8635, SFF-8665, SFF-8685 et
       al).";
    reference
      "SFF-8436;
       SFF-8635;
       SFF-8665;
       SFF-8685;
       SFF-8024 (Revision 4.12) Table 4-1 - Value 0Dh";
  }

  identity cxp-or-later {
    base physical-device;
    description
      "CXP or later.";
    reference
      "SFF-8024 (Revision 4.12) Table 4-1 - Value 0Eh";
  }

  identity shielded-mini-multilane-hd-4x {
    base physical-device;
    description
      "Shielded Mini Multilane HD 4x.";
    reference
      "SFF-8024 (Revision 4.12) Table 4-1 - Value 0Fh";
  }

  identity shielded-mini-multilane-hd-8x {
    base physical-device;
    description
      "Shielded Mini Multilane HD 8x.";
    reference
      "SFF-8024 (Revision 4.12) Table 4-1 - Value 10h";
  }

  identity qsfp28-or-later {
    base physical-device;
    description
      "QSFP28 or later (SFF-8665).";
    reference
      "SFF-8024 (Revision 4.12) Table 4-1 - Value 11h;
       SFF-8665";
  }

  identity cxp2-or-later {
    base physical-device;
    description
      "CXP2 (aka CXP28) or later.";
    reference
      "SFF-8024 (Revision 4.12) Table 4-1 - Value 12h";
  }

  identity cdfp-style1-style2 {
    base physical-device;
    description
      "CDFP (Style 1/Style 2).";
    reference
      "SFF-8024 (Revision 4.12) Table 4-1 - Value 13h";
  }

  identity shielded-mini-multilane-hd-4x-fanout-cable {
    base physical-device;
    description
      "Shielded Mini Multilane HD 4x Fanout Cable.";
    reference
      "SFF-8024 (Revision 4.12) Table 4-1 - Value 14h";
  }

  identity shielded-mini-multilane-hd-8x-fanout-cable {
    base physical-device;
    description
      "Shielded Mini Multilane HD 8x Fanout Cable.";
    reference
      "SFF-8024 (Revision 4.12) Table 4-1 - Value 15h";
  }

  identity cdfp-style3 {
    base physical-device;
    description
      "CDFP (Style 3).";
    reference
      "SFF-8024 (Revision 4.12) Table 4-1 - Value 16h";
  }

  identity micro-qsfp {
    base physical-device;
    description
      "Micro QSFP.";
    reference
      "SFF-8024 (Revision 4.12) Table 4-1 - Value 17h";
  }

  identity qsfp-dd {
    base physical-device;
    description
      "QSFP-DD Double Density 8X Pluggable Transceiver (INF-8628).";
    reference
      "INF-8628;
       SFF-8024 (Revision 4.12) Table 4-1 - Value 18h";
  }

  identity qsfp-8x {
    base physical-device;
    description
      "QSFP 8X Pluggable Transceiver.";
    reference
      "SFF-8024 (Revision 4.12) Table 4-1 - Value 19h";
  }

  identity sfp-dd {
    base physical-device;
    description
      "SFP-DD Double Density 2X Pluggable Transceiver with SFP-DD
       Management Interface Specification.";
    reference
      "SFF-8024 (Revision 4.12) Table 4-1 - Value 1Ah";
  }

  identity dsfp {
    base physical-device;
    description
      "DSFP Dual Small Form Factor Pluggable Transceiver.";
    reference
      "SFF-8024 (Revision 4.12) Table 4-1 - Value 1Bh";
  }

  identity x4-minilink {
    base physical-device;
    description
      "x4 MiniLink/OcuLink.";
    reference
      "SFF-8024 (Revision 4.12) Table 4-1 - Value 1Ch";
  }

  identity x8-minilink {
    base physical-device;
    description
      "x8 MiniLink.";
    reference
      "SFF-8024 (Revision 4.12) Table 4-1 - Value 1Dh";
  }

  identity vendor-specific {
    base physical-device;
    description
      "Vendor-specific physical device. A vendor may derive specific
       identities from this one.";
    reference
      "SFF-8024 (Revision 4.12) Table 4-1 - Values 80h-FFh";
  }

  //Connector Types

  identity connector-type {
    description
      "Identifies the external optical or electrical cable connector
       provided as the media interface.

       This identity is abstract and must not be used to represent a
       connector type.";
    reference
      "SFF-8472 (Revision 12.4) Section 5.3 - Address A0h, Byte 2";
  }

  identity unknown-connector-type {
    base connector-type;
    description
      "Unknown or unspecified.";
    reference
      "SFF-8024 (Revision 4.12) Table 4-3 - Value 00h";
  }

  identity subscriber-connector {
    base connector-type;
    description
      "SC (Subscriber Connector).";
    reference
      "SFF-8024 (Revision 4.12) Table 4-3 - Value 01h";
  }

  identity fibre-channel-style-1-copper {
    base connector-type;
    description
      "Fibre Channel Style 1 copper connector.";
    reference
      "SFF-8024 (Revision 4.12) Table 4-3 - Value 02h";
  }

  identity fibre-channel-style-2-copper {
    base connector-type;
    description
      "Fibre Channel Style 2 copper connector.";
    reference
      "SFF-8024 (Revision 4.12) Table 4-3 - Value 03h";
  }

  identity bnc-tnc {
    base connector-type;
    description
      "BNC/TNC (Bayonet/Threaded Neill-Concelman).";
    reference
      "SFF-8024 (Revision 4.12) Table 4-3 - Value 04h";
  }

  identity fibre-channel-coax-headers {
    base connector-type;
    description
      "Fibre Channel coax headers.";
    reference
      "SFF-8024 (Revision 4.12) Table 4-3 - Value 05h";
  }

  identity fibre-jack {
    base connector-type;
    description
      "Fibre Jack.";
    reference
      "SFF-8024 (Revision 4.12) Table 4-3 - Value 06h";
  }

  identity lucent-connector {
    base connector-type;
    description
      "LC (Lucent Connector).";
    reference
      "SFF-8024 (Revision 4.12) Table 4-3 - Value 07h";
  }

  identity mt-rj {
    base connector-type;
    description
      "MT-RJ (Mechanical Transfer - Registered Jack).";
    reference
      "SFF-8024 (Revision 4.12) Table 4-3 - Value 08h";
  }

  identity mu {
    base connector-type;
    description
      "MU (Multiple Optical).";
    reference
      "SFF-8024 (Revision 4.12) Table 4-3 - Value 09h";
  }

  identity sg {
    base connector-type;
    description
      "SG.";
    reference
      "SFF-8024 (Revision 4.12) Table 4-3 - Value 0Ah";
  }

  identity optical-pigtail {
    base connector-type;
    description
      "Optical Pigtail.";
    reference
      "SFF-8024 (Revision 4.12) Table 4-3 - Value 0Bh";
  }

  identity mpo-1x12 {
    base connector-type;
    description
      "MPO 1x12 (Multifiber Parallel Optic).";
    reference
      "SFF-8024 (Revision 4.12) Table 4-3 - Value 0Ch";
  }

  identity mpo-2x16 {
    base connector-type;
    description
      "MPO 2x16 (Multifiber Parallel Optic).";
    reference
      "SFF-8024 (Revision 4.12) Table 4-3 - Value 0Dh";
  }

  identity hssdc-ii {
    base connector-type;
    description
      "HSSDC II (High Speed Serial Data Connector).";
    reference
      "SFF-8024 (Revision 4.12) Table 4-3 - Value 20h";
  }

  identity copper-pigtail {
    base connector-type;
    description
      "Copper Pigtail.";
    reference
      "SFF-8024 (Revision 4.12) Table 4-3 - Value 21h";
  }

  identity rj45 {
    base connector-type;
    description
      "RF45 (Registered Jack).";
    reference
      "SFF-8024 (Revision 4.12) Table 4-3 - Value 22h";
  }

  identity no-separable-connector {
    base connector-type;
    description
      "No separable connector.";
    reference
      "SFF-8024 (Revision 4.12) Table 4-3 - Value 23h";
  }

  identity mxc-2x16 {
    base connector-type;
    description
      "MXC 2x16.";
    reference
      "SFF-8024 (Revision 4.12) Table 4-3 - Value 24h";
  }

  identity cs-optical-connector {
    base connector-type;
    description
      "CS optical connector.";
    reference
      "SFF-8024 (Revision 4.12) Table 4-3 - Value 25h";
  }

  identity sn-optical-connector {
    base connector-type;
    description
      "SN (previously Mini CS) optical connector.";
    reference
      "SFF-8024 (Revision 4.12) Table 4-3 - Value 26h";
  }

  identity mpo-2x12 {
    base connector-type;
    description
      "MPO 2x12.";
    reference
      "SFF-8024 (Revision 4.12) Table 4-3 - Value 27h";
  }

  identity mpo-1x16 {
    base connector-type;
    description
      "MPO 1x16.";
    reference
      "SFF-8024 (Revision 4.12) Table 4-3 - Value 28h";
  }

  identity power-class {
    description
      "Identifies the higher power classification level supported by
       the transceiver.

       This identity is abstract and must not be used to represent a
       power class.";
    reference
      "SFF-8472 (Revision 12.4) Table 8-3;
       SFF-8436 (Revision 4.9) Table 31;
       SFF-8636 (Revision 2.11) Table 6-16";
  }

  identity power-class-1 {
    base power-class;
    description
      "Power class (level) 1.";
    reference
      "SFF-8472 (Revision 12.4) Table 8-3 - Address A0h, Byte 64, Bits
       6, 5 and 1;
       SFF-8436 (Revision 4.9) Table 31;
       SFF-8636 (Revision 2.11) Table 6-16 - Page 00h, Byte 129, Bits
       7, 6, 5, 1, and 0";
  }

  identity power-class-2 {
    base power-class;
    description
      "Power class (level) 2.";
    reference
      "SFF-8472 (Revision 12.4) Table 8-3 - Address A0h, Byte 64, Bits
       6, 5 and 1;
       SFF-8436 (Revision 4.9) Table 31;
       SFF-8636 (Revision 2.11) Table 6-16 - Page 00h, Byte 129, Bits
       7, 6, 5, 1, and 0";
  }

  identity power-class-3 {
    base power-class;
    description
      "Power class (level) 3.";
    reference
      "SFF-8472 (Revision 12.4) Table 8-3 - Address A0h, Byte 64, Bits
       6, 5 and 1;
       SFF-8436 (Revision 4.9) Table 31;
       SFF-8636 (Revision 2.11) Table 6-16 - Page 00h, Byte 129, Bits
       7, 6, 5, 1, and 0";
  }

  identity power-class-4 {
    base power-class;
    description
      "Power class (level) 4.";
    reference
      "SFF-8472 (Revision 12.4) Table 8-3 - Address A0h, Byte 64, Bits
       6, 5 and 1;
       SFF-8436 (Revision 4.9) Table 31;
       SFF-8636 (Revision 2.11) Table 6-16 - Page 00h, Byte 129, Bits
       7, 6, 5, 1, and 0";
  }

  identity power-class-5 {
    base power-class;
    description
      "Power class (level) 5.";
    reference
      "SFF-8636 (Revision 2.11) Table 6-16 - Page 00h, Byte 129, Bits
       7, 6, 5, 1, and 0";
  }

  identity power-class-6 {
    base power-class;
    description
      "Power class (level) 6.";
    reference
      "SFF-8636 (Revision 2.11) Table 6-16 - Page 00h, Byte 129, Bits
       7, 6, 5, 1, and 0";
  }

  identity power-class-7 {
    base power-class;
    description
      "Power class (level) 7.";
    reference
      "SFF-8636 (Revision 2.11) Table 6-16 - Page 00h, Byte 129, Bits
       7, 6, 5, 1, and 0";
  }

  identity power-class-8 {
    base power-class;
    description
      "Power class (level) 8.";
    reference
      "SFF-8636 (Revision 2.11) Table 6-16 - Page 00h, Byte 129, Bits
       7, 6, 5, 1, and 0";
  }

  typedef power-milliwatts {
    type decimal64 {
      fraction-digits 4;
    }
    units "milliwatts";
    description
      "Defines the power detected at a transceiver in milliwatts.";
  }

  typedef power-dbm {
    type union {
      type enumeration {
        enum undetermined {
          description
            "A value could not be determined or the transceiver
             reports a power value of zero.";
        }
      }
      type decimal64 {
        fraction-digits 4;
        range "-40..20";
      }
    }
    units "dBm";
    description
      "Defines the power detected at a transceiver in dBm.";
  }

  grouping link-parameters {
    description
      "Management data nodes related to the physical link of the
       transceiver.";
    choice wavelength-or-specification-compliance {
      config false;
      description
        "For optical variants, report the nominal transmitter output
         wavelength. For passive and active cable variants, report the
         specification compliance.";
      reference
        "SFF-8472 (Revision 12.4) Section 8.1 - Address A0h,
         Bytes 60-61";
      case unspecified-wavelength-or-cable-specification-compliance {
        leaf unspecified {
          type empty;
          description
            "Neither the laser wavelength or cable specification
             compliance is specified.";
        }
      }
      case wavelength {
        leaf wavelength {
          type uint32;
          units "nanometers";
          description
            "For optical variants, this denotes the nominal
             transmitter output wavelength at room temperature.";
        }
      }
      case high-resolution-wavelength {
        leaf high-resolution-wavelength {
          type decimal64 {
            fraction-digits 2;
          }
          units "nanometers";
          description
            "For optical variants, reports the nominal
             transmitter output wavelength at room temperature.

             This data node is intended to be used for transceiver
             links able to report wavelengths with subnanometer
             granularity.

             However, it may also be used with transceiver links that
             cannot report wavelengths with subnanometer granularity,
             in which case the decimal digits must be set to '.00'.";
          reference
            "SFF-8636 (Revision 2.11) Section 6.3.19;
             INF-8077i (Revision 4.5) Section 5.33";
        }
      }
      case passive-cable-specification-compliance {
        leaf passive-cable-specification-compliance {
          type enumeration {
            enum fc-pi-4-appendix-h {
              description
                "Compliant to FC-PI-4 Appendix H.";
              reference
                "SFF-8472 (Revision 12.4) Table 8-1 - Address A0h,
                 Byte 60, bit 1";
            }
            enum sff-8431-appendix-e {
              description
                "Compliant to SFF-8431 Appendix E.";
              reference
                "SFF-8472 (Revision 12.4) Table 8-1 - Address A0h,
                 Byte 60, bit 0";
            }
          }
          status deprecated;
          description
            "For passive cable variants, this denotes the passive
             cable specification compliance.";
          reference
            "SFF-8472 (Revision 12.4) Table 8-1";
        }
        leaf-list passive-cable-spec-compliance {
          type enumeration {
            enum fc-pi-4-appendix-h {
              description
                "Compliant to FC-PI-4 Appendix H.";
              reference
                "SFF-8472 (Revision 12.4) Table 8-1 - Address A0h,
                 Byte 60, bit 1";
            }
            enum sff-8431-appendix-e {
              description
                "Compliant to SFF-8431 Appendix E.";
              reference
                "SFF-8472 (Revision 12.4) Table 8-1 - Address A0h,
                 Byte 60, bit 0";
            }
          }
          description
            "For passive cable variants, this denotes the passive
             cable specification compliance.";
          reference
            "SFF-8472 (Revision 12.4) Table 8-1";
        }
      }
      case active-cable-specification-compliance {
        leaf active-cable-specification-compliance {
          type enumeration {
            enum fc-pi-4-limiting {
              description
                "Compliant to FC-PI-4 Limiting.";
              reference
                "SFF-8472 (Revision 12.4) Table 8-2 - Address A0h,
                 Byte 60, bit 3";
            }
            enum sff-8431-limiting {
              description
                "Compliant to SFF-8431 Limiting.";
              reference
                "SFF-8472 (Revision 12.4) Table 8-2 - Address A0h,
                 Byte 60, bit 2";
            }
            enum fc-pi-4-appendix-h {
              description
                "Compliant to FC-PI-4 Appendix H.";
              reference
                "SFF-8472 (Revision 12.4) Table 8-2 - Address A0h,
                 Byte 60, bit 1";
            }
            enum sff-8431-appendix-e {
              description
                "Compliant to SFF-8431 Appendix E.";
              reference
                "SFF-8472 (Revision 12.4) Table 8-2 - Address A0h,
                 Byte 60, bit 0";
            }
          }
          status deprecated;
          description
            "For active cable variants, this denotes the active cable
             specification compliance.";
          reference
            "SFF-8472 (Revision 12.4) Table 8-2";
        }
        leaf-list active-cable-spec-compliance {
          type enumeration {
            enum fc-pi-4-limiting {
              description
                "Compliant to FC-PI-4 Limiting.";
              reference
                "SFF-8472 (Revision 12.4) Table 8-2 - Address A0h,
                 Byte 60, bit 3";
            }
            enum sff-8431-limiting {
              description
                "Compliant to SFF-8431 Limiting.";
              reference
                "SFF-8472 (Revision 12.4) Table 8-2 - Address A0h,
                 Byte 60, bit 2";
            }
            enum fc-pi-4-appendix-h {
              description
                "Compliant to FC-PI-4 Appendix H.";
              reference
                "SFF-8472 (Revision 12.4) Table 8-2 - Address A0h,
                 Byte 60, bit 1";
            }
            enum sff-8431-appendix-e {
              description
                "Compliant to SFF-8431 Appendix E.";
              reference
                "SFF-8472 (Revision 12.4) Table 8-2 - Address A0h,
                 Byte 60, bit 0";
            }
          }
          description
            "For active cable variants, this denotes the active cable
             specification compliance.";
          reference
            "SFF-8472 (Revision 12.4) Table 8-2";
        }
      }
    }
  }

  grouping transceiver-diagnostic-parameters {
    description
      "Management data nodes related to retrieving diagnostic data
       from the transceiver.";
    leaf temperature {
      type int32;
      units "millidegrees Celsius";
      config false;
      mandatory true;
      description
        "Internally measured transceiver temperature. Temperature
         accuracy is vendor-specific but must be better than +/- 3
         degrees Celsius over specified operating temperature and
         voltage.";
      reference
        "SFF-8472 (Revision 12.4) Table 9-16 - Address A2h,
         Bytes 96-97";
    }
    leaf supply-voltage {
      type uint16;
      units "0.1 millivolts";
      config false;
      mandatory true;
      description
        "Internally measured transceiver supply voltage. Practical
         considerations to be defined by transceiver manufacturer will
         tend to limit the actual bounds of the supply voltage
         measurement. Accuracy is vendor-specific but must be better
         than +/- 3% of the manufacturer's nominal value over
         specified operating temperature and voltage. Note that in
         some transceivers, transmitter supply voltage and receiver
         supply voltage are isolated. In that case, only one supply
         is monitored. Refer to the device specification for more
         detail.";
      reference
        "SFF-8472 (Revision 12.4) Table 9-16 - Address A2h,
         Bytes 98-99";
    }
  }

  grouping link-diagnostic-parameters {
    description
      "Management data nodes related to retrieving diagnostic physical
       link data from the transceiver.";
    leaf tx-bias {
      type uint32;
      units "microamperes";
      config false;
      mandatory true;
      description
        "Measured transmit (TX) bias current in microamperes (uA).
         Accuracy is vendor-specific but must be better than +/- 10%
         of the manufacturer's nominal value over specified operating
         temperature and voltage.";
      reference
        "SFF-8472 (Revision 12.4) Table 9-16 - Address A2h,
         Bytes 100-101";
    }
    choice power {
      config false;
      status deprecated;
      description
        "Measured receive (RX) and transmit (TX) power.";
      case power-in-mwatt {
        status deprecated;
        leaf tx-power {
          type uint16;
          units "0.1 milliwatts";
          status deprecated;
          description
            "Measured transmit (TX) output power in tenths of a
             milliwatt (mW). Data is assumed to be based on
             measurement of laser monitor photodiode current. It is
             factory calibrated to absolute units using the most
             representative fiber output type. Accuracy is vendor-
             specific but must be better than +/- 3dB over specified
             temperature and voltage. Data is not valid when the
             transmitter is disabled.";
          reference
            "SFF-8472 (Revision 12.4) Table 9-16 - Address A2h,
             Bytes 102-103";
        }
        leaf rx-power {
          type uint16;
          units "0.1 milliwatts";
          status deprecated;
          description
            "Measured received (RX) optical power in tenths of a mW.
             Absolute accuracy is dependent upon the exact optical
             wavelength. For the vendor specified wavelength, accuracy
             shall be better than +/- 3dB over specified temperature
             and voltage. This accuracy shall be maintained for input
             power levels up to the lesser of maximum transmitted or
             maximum received optical power per the appropriate
             standard. It shall be maintained down to the minimum
             transmitted power minus cable plant loss (insertion loss
             or passive loss) per the appropriate standard. Absolute
             accuracy beyond this minimum required received input
             optical power range is vendor-specific.";
          reference
            "SFF-8472 (Revision 12.4) Table 9-16 - Address A2h,
             Bytes 104-105";
        }
      }
    }
    container power-milliwatts {
      presence "Indicates that monitoring of received power and
                transmit power is reported in milliwatts.";
      config false;
      description
        "Data nodes reporting the power levels measured at the
         transceiver link in milliwatts.";
      leaf transmit {
        type power-milliwatts;
        description
          "Measured transmit (TX) output power in milliwatts. Data is
           assumed to be based on measurement of laser monitor
           photodiode current. It is factory calibrated to absolute
           units using the most representative fiber output type.
           Accuracy is vendor-specific but must be better than
           +/- 3dB over specified temperature and voltage. Data is
           not valid when the transmitter is disabled.";
        reference
          "SFF-8472 (Revision 12.4) Table 9-16 - Address A2h,
           Bytes 102-103";
      }
      leaf receive {
        type power-milliwatts;
        description
          "Measured received (RX) optical power in milliwatts.
           Absolute accuracy is dependent upon the exact optical
           wavelength. For the vendor specified wavelength, accuracy
           shall be better than +/- 3dB over specified temperature and
           voltage. This accuracy shall be maintained for input
           power levels up to the lesser of maximum transmitted or
           maximum received optical power per the appropriate
           standard. It shall be maintained down to the minimum
           transmitted power minus cable plant loss (insertion loss
           or passive loss) per the appropriate standard. Absolute
           accuracy beyond this minimum required received input
           optical power range is vendor-specific.";
        reference
          "SFF-8472 (Revision 12.4) Table 9-16 - Address A2h,
           Bytes 104-105";
      }
    }
    container power-dbm {
      if-feature "bbf-hw-xcvr:optical-power-and-sensitivity-in-dbm";
      presence
        "Indicates that monitoring of received power and transmit
         power is reported in dBm.";
      config false;
      description
        "Data nodes reporting the power levels measured at the
         transceiver link in dBm.";
      leaf transmit {
        type power-dbm;
        description
          "Measured transmitted optical power in dBm. Data is assumed
           to be based on measurement of laser monitor photodiode
           current. It is factory calibrated to absolute units using
           the most representative fiber output type. Accuracy is
           vendor-specific but must be better than +/- 3dB over
           specified temperature and voltage. Data is not valid when
           the transmitter is disabled.";
        reference
          "SFF-8472 (Revision 12.4) Table 9-16 - Address A2h,
           Bytes 102-103";
      }
      leaf receive {
        type power-dbm;
        description
          "Measured received optical power in dBm. Absolute accuracy
           is dependent upon the exact optical wavelength. For the
           vendor specified wavelength, accuracy shall be better than
           +/- 3dB over specified temperature and voltage. This
           accuracy shall be maintained for input power levels up to
           the lesser of maximum transmitted or maximum received
           optical power per the appropriate standard. It shall be
           maintained down to the minimum transmitted power minus
           cable plant loss (insertion loss or passive loss) per the
           appropriate standard. Absolute accuracy beyond this minimum
           required received input optical power range is vendor-
           specific.";
        reference
          "SFF-8472 (Revision 12.4) Table 9-16 - Address A2h,
           Bytes 104-105";
      }
    }
    leaf laser-temperature {
      type int32;
      units "millidegrees Celsius";
      config false;
      description
        "Measured optional laser temperature. The relative and
         absolute accuracy are vendor-specific but relative laser
         temperature accuracy must be better than +/- 0.2 degrees
         Celsius. [Relative temperature accuracy refers to the
         accuracy of the reported temperature changes relative to the
         actual laser temperature changes.";
      reference
        "SFF-8472 (Revision 12.4) Table 9-16 - Address A2h,
         Bytes 106-107";
    }
    leaf tec-current {
      type int16;
      units "0.1 milliamperes";
      config false;
      description
        "Measured Thermoelectric Cooler (TEC) current. The format is
         signed two's complement with the LSB equal to 0.1 milliampere
         (mA). Thus a range from -3276.8 to +3276.7 mA may be reported
         with a resolution of 0.1 mA. Reported TEC current is a
         positive number for cooling and a negative number for
         heating. The accuracy of the TEC current monitor is vendor-
         specific but must be better than +/- 15% of the maximum TEC
         current as stored in the TEC current high alarm threshold.";
      reference
        "SFF-8472 (Revision 12.4) Table 9-16 - Address A2h,
         Bytes 108-109";
    }
  }

  grouping transceiver-alarm-diagnostic-parameters {
    description
      "Management data nodes related to retrieving diagnostic basic
       alarm data from the transceiver.";
    leaf-list alarm-flag {
      type identityref {
        base transceiver-alarm-warning;
      }
      config false;
      description
        "Alarm flags associated with transceiver temperature and
         supply voltage as well as reserved locations for future
         flags. Alarm flags indicate conditions likely to be
         associated with an in-operational link and cause for
         immediate action.";
      reference
        "SFF-8472 (Revision 12.4) Table 9-7 - Address A2h,
         Bytes 112-117;
         SFF-8436 (Revision 4.9) Table 25 - Page A0h,
         Addresses 100-106";
    }
    leaf-list warning-flag {
      type identityref {
        base transceiver-alarm-warning;
      }
      config false;
      description
        "Warning flags associated with transceiver temperature and
         supply voltage as well as reserved locations for future
         flags. Warning flags indicate conditions outside the normally
         guaranteed bounds but not necessarily causes of immediate
         link failures. Certain warning flags may also be defined by
         the manufacturer as end-of-life indicators (such as for
         higher than expected bias currents in a constant power
         control loop).";
      reference
        "SFF-8472 (Revision 12.4) Table 9-17 - Address A2h,
         Bytes 112-117;
         SFF-8436 (Revision 4.9) Table 25 - Page A0h,
         Addresses 100-106";
    }
  }

  grouping link-alarm-diagnostic-parameters {
    description
      "Management data nodes related to retrieving diagnostic physical
       link alarm data from the transceiver.";
    leaf-list alarm-flag {
      type identityref {
        base link-alarm-warning;
      }
      config false;
      description
        "Alarm flags associated with the transceiver transmit bias
         current, transmit output power and received optical power as
         well as reserved locations for future flags. Alarm flags
         indicate conditions likely to be associated with an
         in-operational link and cause for immediate action.";
      reference
        "SFF-8472 (Revision 12.4) Table 9-7 - Address A2h,
         Bytes 112-117;
         SFF-8436 (Revision 4.9) Table 25 - Page A0h,
         Addresses 100-106";
    }
    leaf-list warning-flag {
      type identityref {
        base link-alarm-warning;
      }
      config false;
      description
        "Warning flags associated with the transceiver transmit bias
         current, transmit output power and received optical power as
         well as reserved locations for future flags. Warning flags
         indicate conditions outside the normally guaranteed bounds
         but not necessarily causes of immediate link failures.
         Certain warning flags may also be defined by the manufacturer
         as end-of-life indicators (such as for higher than expected
         bias currents in a constant power control loop).";
      reference
        "SFF-8472 (Revision 12.4) Table 9-7 - Address A2h,
         Bytes 112-117;
         SFF-8436 (Revision 4.9) Table 25 - Page A0h,
         Addresses 100-106";
    }
  }

  grouping transceiver-compliance-codes {
    description
      "Nodes which allow reporting of the transceivers compliance.";
    container compliance-codes {
      status deprecated;
      description
        "Compliance codes which collectively represent the electronic
         or optical interfaces that are supported by the
         transceiver.";
      reference
        "SFF-8472 (Revision 12.4) Table 5-3 - Address A0h,
         Bytes 3-10, 36, 62";
      leaf ten-gigabit-ethernet {
        type enumeration {
          enum not-applicable {
            description
              "Not applicable.";
          }
          enum 10g-base-er {
            description
              "10G Base-ER.";
            reference
              "SFF-8472 (Revision 12.4) Table 5-3 - Address A0h,
               Byte 3, bit 7";
          }
          enum 10g-base-lrm {
            description
              "10G Base-LRM.";
            reference
              "SFF-8472 (Revision 12.4) Table 5-3 - Address A0h,
               Byte 3, bit 6";
          }
          enum 10g-base-lr {
            description
              "10G Base-LR.";
            reference
              "SFF-8472 (Revision 12.4) Table 5-3 - Address A0h,
               Byte 3, bit 5";
          }
          enum 10g-base-sr {
            description
              "10G Base-SR.";
            reference
              "SFF-8472 (Revision 12.4) Table 5-3 - Address A0h,
               Byte 3, bit 4";
          }
        }
        config false;
        status deprecated;
        description
          "10G Ethernet Compliance Codes.";
      }
      leaf infiniband {
        type enumeration {
          enum not-applicable {
            description
              "Not applicable.";
          }
          enum 1x-sx {
            description
              "1X SX.";
            reference
              "SFF-8472 (Revision 12.4) Table 5-3 - Address A0h,
               Byte 3, bit 3";
          }
          enum 1x-lx {
            description
              "1X LX.";
            reference
              "SFF-8472 (Revision 12.4) Table 5-3 - Address A0h,
               Byte 3, bit 2";
          }
          enum 1x-copper-active {
            description
              "1X Copper Active.";
            reference
              "SFF-8472 (Revision 12.4) Table 5-3 - Address A0h,
               Byte 3, bit 1";
          }
          enum 1x-copper-passive {
            description
              "1X Copper Passive.";
            reference
              "SFF-8472 (Revision 12.4) Table 5-3 - Address A0h,
               Byte 3, bit 0";
          }
        }
        config false;
        status deprecated;
        description
          "Infiniband Compliance Codes.";
      }
      leaf escon {
        type enumeration {
          enum not-applicable {
            description
              "Not applicable.";
          }
          enum escon-mmf {
            description
              "ESCON MMF, 1310nm LED.";
            reference
              "SFF-8472 (Revision 12.4) Table 5-3 - Address A0h,
               Byte 4, bit 7";
          }
          enum escon-smf {
            description
              "ESCON SMF, 1310nm Laser.";
            reference
              "SFF-8472 (Revision 12.4) Table 5-3 - Address A0h,
               Byte 4, bit 6";
          }
        }
        config false;
        status deprecated;
        description
          "ESCON Compliance Codes.";
      }
      leaf sonet {
        type enumeration {
          enum not-applicable {
            description
              "Not applicable.";
          }
          enum oc-192-short-reach {
            description
              "OC-192, short reach.";
            reference
              "SFF-8472 (Revision 12.4) Table 5-3 - Address A0h,
               Byte 4, bit 5";
          }
          enum sonet-reach-specifier-bit1 {
            description
              "SONET reach specifier bit 1.";
            reference
              "SFF-8472 (Revision 12.4) Table 5-3 - Address A0h,
               Byte 4, bit 4";
          }
          enum sonet-reach-specifier-bit2 {
            description
              "SONET reach specifier bit 2.";
            reference
              "SFF-8472 (Revision 12.4) Table 5-3 - Address A0h,
               Byte 4, bit 3";
          }
          enum oc-48-long-reach {
            description
              "OC-48, long reach.";
            reference
              "SFF-8472 (Revision 12.4) Table 5-3 - Address A0h,
               Byte 4, bit 2";
          }
          enum oc-48-intermediate-reach {
            description
              "OC-48, intermediate reach.";
            reference
              "SFF-8472 (Revision 12.4) Table 5-3 - Address A0h,
               Byte 4, bit 1";
          }
          enum oc-48-short-reach {
            description
              "OC-48, short reach.";
            reference
              "SFF-8472 (Revision 12.4) Table 5-3 - Address A0h,
               Byte 4, bit 0";
          }
          enum oc-12-single-mode-long-reach {
            description
              "OC-12, single mode, long reach.";
            reference
              "SFF-8472 (Revision 12.4) Table 5-3 - Address A0h,
               Byte 5, bit 6";
          }
          enum oc-12-single-mode-intermediate-reach {
            description
              "OC-12, single mode, intermediate reach.";
            reference
              "SFF-8472 (Revision 12.4) Table 5-3 - Address A0h,
               Byte 5, bit 5";
          }
          enum oc-12-short-reach {
            description
              "OC-12, short reach.";
            reference
              "SFF-8472 (Revision 12.4) Table 5-3 - Address A0h,
               Byte 5, bit 4";
          }
          enum oc-3-single-mode-long-reach {
            description
              "OC-3, single mode, long reach.";
            reference
              "SFF-8472 (Revision 12.4) Table 5-3 - Address A0h,
               Byte 5, bit 2";
          }
          enum oc-3-single-mode-intermediate-reach {
            description
              "OC-3, single mode, intermediate reach.";
            reference
              "SFF-8472 (Revision 12.4) Table 5-3 - Address A0h,
               Byte 5, bit 1";
          }
          enum oc-3-short-reach {
            description
              "OC-3, short reach.";
            reference
              "SFF-8472 (Revision 12.4) Table 5-3 - Address A0h,
               Byte 5, bit 0";
          }
        }
        config false;
        status deprecated;
        description
          "SONET Compliance Codes.";
      }
      leaf ethernet {
        type enumeration {
          enum not-applicable {
            description
              "Not applicable.";
          }
          enum base-px {
            description
              "BASE-PX.";
            reference
              "SFF-8472 (Revision 12.4) Table 5-3 - Address A0h,
               Byte 6, bit 7";
          }
          enum base-bx10 {
            description
              "BASE-BX10.";
            reference
              "SFF-8472 (Revision 12.4) Table 5-3 - Address A0h,
               Byte 6, bit 6";
          }
          enum 100base-fx {
            description
              "100BASE-FX.";
            reference
              "SFF-8472 (Revision 12.4) Table 5-3 - Address A0h,
               Byte 6, bit 5";
          }
          enum 100base-lx-or-lx-10 {
            description
              "100BASE-LX/LX-10.";
            reference
              "SFF-8472 (Revision 12.4) Table 5-3 - Address A0h,
               Byte 6, bit 4";
          }
          enum 1000base-t {
            description
              "1000BASE-T.";
            reference
              "SFF-8472 (Revision 12.4) Table 5-3 - Address A0h,
               Byte 6, bit 3";
          }
          enum 1000base-cx {
            description
              "1000BASE-CX.";
            reference
              "SFF-8472 (Revision 12.4) Table 5-3 - Address A0h,
               Byte 6, bit 2";
          }
          enum 1000base-lx {
            description
              "1000BASE-LX.";
            reference
              "SFF-8472 (Revision 12.4) Table 5-3 - Address A0h,
               Byte 6, bit 1";
          }
          enum 1000base-sx {
            description
              "1000BASE-SX.";
            reference
              "SFF-8472 (Revision 12.4) Table 5-3 - Address A0h,
               Byte 6, bit 0";
          }
        }
        config false;
        status deprecated;
        description
          "Ethernet Compliance Codes.";
      }
      leaf fibre-channel-link-length {
        type enumeration {
          enum not-applicable {
            description
              "Not applicable.";
          }
          enum very-long-distance {
            description
              "Very long distance (V).";
            reference
              "SFF-8472 (Revision 12.4) Table 5-3 - Address A0h,
               Byte 7, bit 7";
          }
          enum short-distance {
            description
              "Short distance (S).";
            reference
              "SFF-8472 (Revision 12.4) Table 5-3 - Address A0h,
               Byte 7, bit 6";
          }
          enum intermediate-distance {
            description
              "Intermediate distance (I).";
            reference
              "SFF-8472 (Revision 12.4) Table 5-3 - Address A0h,
               Byte 7, bit 5";
          }
          enum long-distance {
            description
              "Long distance (L).";
            reference
              "SFF-8472 (Revision 12.4) Table 5-3 - Address A0h,
               Byte 7, bit 4";
          }
          enum medium-distance {
            description
              "Medium distance (M).";
            reference
              "SFF-8472 (Revision 12.4) Table 5-3 - Address A0h,
               Byte 7, bit 3";
          }
        }
        config false;
        status deprecated;
        description
          "Fibre channel link length.";
      }
      leaf fibre-channel-technology {
        type enumeration {
          enum not-applicable {
            description
              "Not applicable.";
          }
          enum shortwave-laser-linear {
            description
              "Shortwave laser, linear (SA).";
            reference
              "SFF-8472 (Revision 12.4) Table 5-3 - Address A0h,
               Byte 7, bit 2";
          }
          enum longwave-laser-lc {
            description
              "Longwave laser (LC).";
            reference
              "SFF-8472 (Revision 12.4) Table 5-3 - Address A0h,
               Byte 7, bit 1";
          }
          enum electrical-inter-enclosure {
            description
              "Electrical inter-enclosure (EL).";
            reference
              "SFF-8472 (Revision 12.4) Table 5-3 - Address A0h,
               Byte 7, bit 0";
          }
          enum electrical-intra-enclosure {
            description
              "Electrical intra-enclosure (EL).";
            reference
              "SFF-8472 (Revision 12.4) Table 5-3 - Address A0h,
               Byte 8, bit 7";
          }
          enum shortwave-laser-without-ofc {
            description
              "Shortwave laser w/o OFC (SN).";
            reference
              "SFF-8472 (Revision 12.4) Table 5-3 - Address A0h,
               Byte 8, bit 6";
          }
          enum shortwave-laser-with-ofc {
            description
              "Shortwave laser with OFC (SL).";
            reference
              "SFF-8472 (Revision 12.4) Table 5-3 - Address A0h,
               Byte 8, bit 5";
          }
          enum longwave-laser-ll {
            description
              "Longwave laser (LL).";
            reference
              "SFF-8472 (Revision 12.4) Table 5-3 - Address A0h,
               Byte 8, bit 4";
          }
        }
        config false;
        status deprecated;
        description
          "Fibre channel technology.";
      }
      leaf sfp-plus-cable-technology {
        type enumeration {
          enum not-applicable {
            description
              "Not applicable.";
          }
          enum active-cable {
            description
              "Active Cable.";
            reference
              "SFF-8472 (Revision 12.4) Table 5-3 - Address A0h,
               Byte 8, bit 3";
          }
          enum passive-cable {
            description
              "Passive Cable.";
            reference
              "SFF-8472 (Revision 12.4) Table 5-3 - Address A0h,
               Byte 8, bit 2";
          }
        }
        config false;
        status deprecated;
        description
          "SFP+ cable technology.";
      }
      leaf fibre-channel-transmission-media {
        type enumeration {
          enum not-applicable {
            description
              "Not applicable.";
          }
          enum twin-axial-pair {
            description
              "Twin Axial Pair (TW).";
            reference
              "SFF-8472 (Revision 12.4) Table 5-3 - Address A0h,
               Byte 9, bit 7";
          }
          enum twin-twisted-pair {
            description
              "Twin Twisted Pair (TP).";
            reference
              "SFF-8472 (Revision 12.4) Table 5-3 - Address A0h,
               Byte 9, bit 6";
          }
          enum miniature-coax {
            description
              "Miniature Coax (MI).";
            reference
              "SFF-8472 (Revision 12.4) Table 5-3 - Address A0h,
               Byte 9, bit 5";
          }
          enum video-coax {
            description
              "Video Coax (TV).";
            reference
              "SFF-8472 (Revision 12.4) Table 5-3 - Address A0h,
               Byte 9, bit 4";
          }
          enum multimode-62.5um {
            description
              "Multimode, 62.5um (M6).";
            reference
              "SFF-8472 (Revision 12.4) Table 5-3 - Address A0h,
               Byte 9, bit 3";
          }
          enum multimode-50um {
            description
              "Multimode, 50um (M5 or M5E).";
            reference
              "SFF-8472 (Revision 12.4) Table 5-3 - Address A0h,
               Byte 9, bit 2";
          }
          enum single-mode {
            description
              "Single Mode (SM).";
            reference
              "SFF-8472 (Revision 12.4) Table 5-3 - Address A0h,
               Byte 9, bit 0";
          }
        }
        config false;
        status deprecated;
        description
          "Fibre channel transmission media.";
      }
      leaf fibre-channel-speed {
        type enumeration {
          enum not-applicable {
            description
              "Not applicable.";
          }
          enum 1200-mbytes-sec {
            description
              "1200 MBytes/sec.";
            reference
              "SFF-8472 (Revision 12.4) Table 5-3 - Address A0h,
               Byte 10, bit 7";
          }
          enum 800-mbytes-sec {
            description
              "800 MBytes/sec.";
            reference
              "SFF-8472 (Revision 12.4) Table 5-3 - Address A0h,
               Byte 10, bit 6";
          }
          enum 1000-mbytes-sec {
            status deprecated;
            description
              "This enum was mistakenly defined to represent the value
               1600 MBytes/sec and is now deprecated. A new enum,
               '1600-mbytes-sec' has been defined and should be used
               to represent 1600 MBytes/sec.";
            reference
              "SFF-8472 (Revision 12.4) Table 5-3 - Address A0h,
               Byte 10, bit 5";
          }
          enum 400-mbytes-sec {
            description
              "400 MBytes/sec.";
            reference
              "SFF-8472 (Revision 12.4) Table 5-3 - Address A0h,
               Byte 10, bit 4";
          }
          enum 3200-mbytes-sec {
            description
              "3200 MBytes/sec.";
            reference
              "SFF-8472 (Revision 12.4) Table 5-3 - Address A0h,
               Byte 10, bit 3";
          }
          enum 200-mbytes-sec {
            description
              "200 MBytes/sec.";
            reference
              "SFF-8472 (Revision 12.4) Table 5-3 - Address A0h,
               Byte 10, bit 2";
          }
          enum 100-mbytes-sec {
            description
              "100 MBytes/sec.";
            reference
              "SFF-8472 (Revision 12.4) Table 5-3 - Address A0h,
               Byte 10, bit 0";
          }
          enum 1600-mbytes-sec {
            description
              "1600 MBytes/sec.";
            reference
              "SFF-8472 (Revision 12.4) Table 5-3 - Address A0h,
               Byte 10, bit 5";
          }
        }
        config false;
        status deprecated;
        description
          "Fibre channel speed.";
      }
    }
    container codes {
      description
        "Compliance codes which collectively represent the electronic
         or optical interfaces that are supported by the
         transceiver.";
      reference
        "SFF-8472 (Revision 12.4) Table 5-3 - Address A0h,
         Bytes 3-10, 36, 62;
         SFF-8436 (Revision 4.9) Table 33 - Page 00h,
         Addresses 131-138;
         SFF-8636 (Revision 2.11) Table 6-17 - Page 00h,
         Bytes 131-138";
      leaf-list ten-gigabit-ethernet {
        type enumeration {
          enum 10g-base-er {
            description
              "10G Base-ER.";
            reference
              "SFF-8472 (Revision 12.4) Table 5-3 - Address A0h,
               Byte 3, bit 7";
          }
          enum 10g-base-lrm {
            description
              "10G Base-LRM.";
            reference
              "SFF-8472 (Revision 12.4) Table 5-3 - Address A0h,
               Byte 3, bit 6;
               SFF-8436 (Revision 4.9) Table 33 - Page 00h,
               Address 131, bit 6;
               SFF-8636 (Revision 2.11) Table 6-17 - Page 00h,
               Byte 131, bit 6";
          }
          enum 10g-base-lr {
            description
              "10G Base-LR.";
            reference
              "SFF-8472 (Revision 12.4) Table 5-3 - Address A0h,
               Byte 3, bit 5;
               SFF-8436 (Revision 4.9) Table 33 - Page 00h,
               Address 131, bit 5;
               SFF-8636 (Revision 2.11) Table 6-17 - Page 00h,
               Byte 131, bit 5";
          }
          enum 10g-base-sr {
            description
              "10G Base-SR.";
            reference
              "SFF-8472 (Revision 12.4) Table 5-3 - Address A0h,
               Byte 3, bit 4;
               SFF-8436 (Revision 4.9) Table 33 - Page 00h,
               Address 131, bit 4;
               SFF-8636 (Revision 2.11) Table 6-17 - Page 00h,
               Byte 131, bit 4";
          }
        }
        config false;
        description
          "10G Ethernet Compliance Codes.";
      }
      leaf-list forty-gigabit-ethernet {
        type enumeration {
          enum 40g-base-cr4 {
            description
              "40G Base-CR4.";
            reference
              "SFF-8436 (Revision 4.9) Table 33 - Page 00h,
               Address 131, bit 3;
               SFF-8636 (Revision 2.11) Table 6-17 - Page 00h,
               Byte 131, bit 3";
          }
          enum 40g-base-sr4 {
            description
              "40G Base-SR4.";
            reference
              "SFF-8436 (Revision 4.9) Table 33 - Page 00h,
               Address 131, bit 2;
               SFF-8636 (Revision 2.11) Table 6-17 - Page 00h,
               Byte 131, bit 2";
          }
          enum 40g-base-lr4 {
            description
              "40G Base-LR4.";
            reference
              "SFF-8436 (Revision 4.9) Table 33 - Page 00h,
               Address 131, bit 1;
               SFF-8636 (Revision 2.11) Table 6-17 - Page 00h,
               Byte 131, bit 1";
          }
          enum 40g-active-cable {
            description
              "40G Active Cable (XLPPI).";
            reference
              "SFF-8436 (Revision 4.9) Table 33 - Page 00h,
               Address 131, bit 0;
               SFF-8636 (Revision 2.11) Table 6-17 - Page 00h,
               Byte 131, bit 0";
          }
        }
        config false;
        description
          "40G Ethernet Compliance Codes.";
      }
      leaf-list infiniband {
        type enumeration {
          enum 1x-sx {
            description
              "1X SX.";
            reference
              "SFF-8472 (Revision 12.4) Table 5-3 - Address A0h,
               Byte 3, bit 3";
          }
          enum 1x-lx {
            description
              "1X LX.";
            reference
              "SFF-8472 (Revision 12.4) Table 5-3 - Address A0h,
               Byte 3, bit 2";
          }
          enum 1x-copper-active {
            description
              "1X Copper Active.";
            reference
              "SFF-8472 (Revision 12.4) Table 5-3 - Address A0h,
               Byte 3, bit 1";
          }
          enum 1x-copper-passive {
            description
              "1X Copper Passive.";
            reference
              "SFF-8472 (Revision 12.4) Table 5-3 - Address A0h,
               Byte 3, bit 0";
          }
        }
        config false;
        description
          "InfiniBand (IB) Compliance Codes.";
      }
      leaf-list escon {
        type enumeration {
          enum escon-mmf {
            description
              "ESCON MMF, 1310nm LED.";
            reference
              "SFF-8472 (Revision 12.4) Table 5-3 - Address A0h,
               Byte 4, bit 7";
          }
          enum escon-smf {
            description
              "ESCON SMF, 1310nm Laser.";
            reference
              "SFF-8472 (Revision 12.4) Table 5-3 - Address A0h,
               Byte 4, bit 6";
          }
        }
        config false;
        description
          "ESCON Compliance Codes.";
      }
      leaf-list sonet {
        type enumeration {
          enum oc-192-short-reach {
            description
              "OC-192, short reach.";
            reference
              "SFF-8472 (Revision 12.4) Table 5-3 - Address A0h,
               Byte 4, bit 5";
          }
          enum sonet-reach-specifier-bit1 {
            description
              "SONET reach specifier bit 1.";
            reference
              "SFF-8472 (Revision 12.4) Table 5-3 - Address A0h,
               Byte 4, bit 4";
          }
          enum sonet-reach-specifier-bit2 {
            description
              "SONET reach specifier bit 2.";
            reference
              "SFF-8472 (Revision 12.4) Table 5-3 - Address A0h,
               Byte 4, bit 3";
          }
          enum oc-48-long-reach {
            description
              "OC-48, long reach.";
            reference
              "SFF-8472 (Revision 12.4) Table 5-3 - Address A0h,
               Byte 4, bit 2;
               SFF-8436 (Revision 4.9) Table 33 - Page 00h,
               Address 132, bit 2;
               SFF-8636 (Revision 2.11) Table 6-17 - Page 00h,
               Byte 132, bit 2";
          }
          enum oc-48-intermediate-reach {
            description
              "OC-48, intermediate reach.";
            reference
              "SFF-8472 (Revision 12.4) Table 5-3 - Address A0h,
               Byte 4, bit 1;
               SFF-8436 (Revision 4.9) Table 33 - Page 00h,
               Address 132, bit 1;
               SFF-8636 (Revision 2.11) Table 6-17 - Page 00h,
               Byte 132, bit 1";
          }
          enum oc-48-short-reach {
            description
              "OC-48, short reach.";
            reference
              "SFF-8472 (Revision 12.4) Table 5-3 - Address A0h,
               Byte 4, bit 0;
               SFF-8436 (Revision 4.9) Table 33 - Page 00h,
               Address 132, bit 0;
               SFF-8636 (Revision 2.11) Table 6-17 - Page 00h,
               Byte 132, bit 0";
          }
          enum oc-12-single-mode-long-reach {
            description
              "OC-12, single mode, long reach.";
            reference
              "SFF-8472 (Revision 12.4) Table 5-3 - Address A0h,
               Byte 5, bit 6";
          }
          enum oc-12-single-mode-intermediate-reach {
            description
              "OC-12, single mode, intermediate reach.";
            reference
              "SFF-8472 (Revision 12.4) Table 5-3 - Address A0h,
               Byte 5, bit 5";
          }
          enum oc-12-short-reach {
            description
              "OC-12, short reach.";
            reference
              "SFF-8472 (Revision 12.4) Table 5-3 - Address A0h,
               Byte 5, bit 4";
          }
          enum oc-3-single-mode-long-reach {
            description
              "OC-3, single mode, long reach.";
            reference
              "SFF-8472 (Revision 12.4) Table 5-3 - Address A0h,
               Byte 5, bit 2";
          }
          enum oc-3-single-mode-intermediate-reach {
            description
              "OC-3, single mode, intermediate reach.";
            reference
              "SFF-8472 (Revision 12.4) Table 5-3 - Address A0h,
               Byte 5, bit 1";
          }
          enum oc-3-short-reach {
            description
              "OC-3, short reach.";
            reference
              "SFF-8472 (Revision 12.4) Table 5-3 - Address A0h,
               Byte 5, bit 0";
          }
          enum 40g-otn {
            description
              "40G OTN (OTU3B/OTU3C).";
            reference
              "SFF-8436 (Revision 4.9) Table 33 - Page 00h,
               Address 132, bit 3";
          }
        }
        config false;
        description
          "SONET Compliance Codes.";
      }
      leaf-list sas-sata {
        type enumeration {
          enum sas-24.0-gbps {
            description
              "SAS 24.0 Gbps.";
            reference
              "SFF-8636 (Revision 2.11) Table 6-17 - Page 00h,
               Byte 133, bit 7";
          }
          enum sas-12.0-gbps {
            description
              "SAS 12.0 Gbps.";
            reference
              "SFF-8636 (Revision 2.11) Table 6-17 - Page 00h,
               Byte 133, bit 6";
          }
          enum sas-6.0-gbps {
            description
              "SAS 6.0 Gbps.";
            reference
              "SFF-8436 (Revision 4.9) Table 33 - Page 00h,
               Address 133, bit 5;
               SFF-8636 (Revision 2.11) Table 6-17 - Page 00h,
               Byte 133, bit 5";
          }
          enum sas-3.0-gbps {
            description
              "SAS 3.0 Gbps.";
            reference
              "SFF-8436 (Revision 4.9) Table 33 - Page 00h,
               Address 133, bit 4;
               SFF-8636 (Revision 2.11) Table 6-17 - Page 00h,
               Byte 133, bit 4";
          }
        }
        config false;
        description
          "SAS/SATA Compliance Codes.";
      }
      leaf-list ethernet {
        type enumeration {
          enum base-px {
            description
              "BASE-PX.";
            reference
              "SFF-8472 (Revision 12.4) Table 5-3 - Address A0h,
               Byte 6, bit 7";
          }
          enum base-bx10 {
            description
              "BASE-BX10.";
            reference
              "SFF-8472 (Revision 12.4) Table 5-3 - Address A0h,
               Byte 6, bit 6";
          }
          enum 100base-fx {
            description
              "100BASE-FX.";
            reference
              "SFF-8472 (Revision 12.4) Table 5-3 - Address A0h,
               Byte 6, bit 5";
          }
          enum 100base-lx-or-lx-10 {
            description
              "100BASE-LX/LX-10.";
            reference
              "SFF-8472 (Revision 12.4) Table 5-3 - Address A0h,
               Byte 6, bit 4";
          }
          enum 1000base-t {
            description
              "1000BASE-T.";
            reference
              "SFF-8472 (Revision 12.4) Table 5-3 - Address A0h,
               Byte 6, bit 3;
               SFF-8436 (Revision 4.9) Table 33 - Page 00h,
               Address 134, bit 3;
               SFF-8636 (Revision 2.11) Table 6-17 - Page 00h,
               Byte 134, bit 3";
          }
          enum 1000base-cx {
            description
              "1000BASE-CX.";
            reference
              "SFF-8472 (Revision 12.4) Table 5-3 - Address A0h,
               Byte 6, bit 2;
               SFF-8436 (Revision 4.9) Table 33 - Page 00h,
               Address 134, bit 2;
               SFF-8636 (Revision 2.11) Table 6-17 - Page 00h,
               Byte 134, bit 2";
          }
          enum 1000base-lx {
            description
              "1000BASE-LX.";
            reference
              "SFF-8472 (Revision 12.4) Table 5-3 - Address A0h,
               Byte 6, bit 1;
               SFF-8436 (Revision 4.9) Table 33 - Page 00h,
               Address 134, bit 1;
               SFF-8636 (Revision 2.11) Table 6-17 - Page 00h,
               Byte 134, bit 1";
          }
          enum 1000base-sx {
            description
              "1000BASE-SX.";
            reference
              "SFF-8472 (Revision 12.4) Table 5-3 - Address A0h,
               Byte 6, bit 0;
               SFF-8436 (Revision 4.9) Table 33 - Page 00h,
               Address 134, bit 0;
               SFF-8636 (Revision 2.11) Table 6-17 - Page 00h,
               Byte 134, bit 0";
          }
        }
        config false;
        description
          "Ethernet Compliance Codes.";
      }
      leaf-list fibre-channel-link-length {
        type enumeration {
          enum very-long-distance {
            description
              "Very long distance (V).";
            reference
              "SFF-8472 (Revision 12.4) Table 5-3 - Address A0h,
               Byte 7, bit 7;
               SFF-8436 (Revision 4.9) Table 33 - Page 00h,
               Address 135, bit 7;
               SFF-8636 (Revision 2.11) Table 6-17 - Page 00h,
               Byte 135, bit 7";
          }
          enum short-distance {
            description
              "Short distance (S).";
            reference
              "SFF-8472 (Revision 12.4) Table 5-3 - Address A0h,
               Byte 7, bit 6;
               SFF-8436 (Revision 4.9) Table 33 - Page 00h,
               Address 135, bit 6;
               SFF-8636 (Revision 2.11) Table 6-17 - Page 00h,
               Byte 135, bit 6";
          }
          enum intermediate-distance {
            description
              "Intermediate distance (I).";
            reference
              "SFF-8472 (Revision 12.4) Table 5-3 - Address A0h,
               Byte 7, bit 5;
               SFF-8436 (Revision 4.9) Table 33 - Page 00h,
               Address 135, bit 5;
               SFF-8636 (Revision 2.11) Table 6-17 - Page 00h,
               Byte 135, bit 5";
          }
          enum long-distance {
            description
              "Long distance (L).";
            reference
              "SFF-8472 (Revision 12.4) Table 5-3 - Address A0h,
               Byte 7, bit 4;
               SFF-8436 (Revision 4.9) Table 33 - Page 00h,
               Address 135, bit 4;
               SFF-8636 (Revision 2.11) Table 6-17 - Page 00h,
               Byte 135, bit 4";
          }
          enum medium-distance {
            description
              "Medium distance (M).";
            reference
              "SFF-8472 (Revision 12.4) Table 5-3 - Address A0h,
               Byte 7, bit 3;
               SFF-8436 (Revision 4.9) Table 33 - Page 00h,
               Address 135, bit 3;
               SFF-8636 (Revision 2.11) Table 6-17 - Page 00h,
               Byte 135, bit 3";
          }
        }
        config false;
        description
          "Fibre channel link length.";
      }
      leaf-list fibre-channel-technology {
        type enumeration {
          enum shortwave-laser-linear {
            description
              "Shortwave laser, linear (SA).";
            reference
              "SFF-8472 (Revision 12.4) Table 5-3 - Address A0h,
               Byte 7, bit 2";
          }
          enum longwave-laser-lc {
            description
              "Longwave laser (LC).";
            reference
              "SFF-8472 (Revision 12.4) Table 5-3 - Address A0h,
               Byte 7, bit 1;
               SFF-8436 (Revision 4.9) Table 33 - Page 00h,
               Address 135, bit 1;
               SFF-8636 (Revision 2.11) Table 6-17 - Page 00h,
               Byte 135, bit 1";
          }
          enum electrical-inter-enclosure {
            description
              "Electrical inter-enclosure (EL).";
            reference
              "SFF-8472 (Revision 12.4) Table 5-3 - Address A0h,
               Byte 7, bit 0;
               SFF-8436 (Revision 4.9) Table 33 - Page 00h,
               Address 135, bit 0;
               SFF-8636 (Revision 2.11) Table 6-17 - Page 00h,
               Byte 135, bit 0";
          }
          enum electrical-intra-enclosure {
            description
              "Electrical intra-enclosure (EL).";
            reference
              "SFF-8472 (Revision 12.4) Table 5-3 - Address A0h,
               Byte 8, bit 7;
               SFF-8436 (Revision 4.9) Table 33 - Page 00h,
               Address 136, bit 7;
               SFF-8636 (Revision 2.11) Table 6-17 - Page 00h,
               Byte 136, bit 7";
          }
          enum shortwave-laser-without-ofc {
            description
              "Shortwave laser w/o OFC (SN).";
            reference
              "SFF-8472 (Revision 12.4) Table 5-3 - Address A0h,
               Byte 8, bit 6;
               SFF-8436 (Revision 4.9) Table 33 - Page 00h,
               Address 136, bit 6;
               SFF-8636 (Revision 2.11) Table 6-17 - Page 00h,
               Byte 136, bit 6";
          }
          enum shortwave-laser-with-ofc {
            description
              "Shortwave laser with OFC (SL).";
            reference
              "SFF-8472 (Revision 12.4) Table 5-3 - Address A0h,
               Byte 8, bit 5;
               SFF-8436 (Revision 4.9) Table 33 - Page 00h,
               Address 136, bit 5;
               SFF-8636 (Revision 2.11) Table 6-17 - Page 00h,
               Byte 136, bit 5";
          }
          enum longwave-laser-ll {
            description
              "Longwave laser (LL).";
            reference
              "SFF-8472 (Revision 12.4) Table 5-3 - Address A0h,
               Byte 8, bit 4;
               SFF-8436 (Revision 4.9) Table 33 - Page 00h,
               Address 136, bit 4;
               SFF-8636 (Revision 2.11) Table 6-17 - Page 00h,
               Byte 136, bit 4";
          }
        }
        config false;
        description
          "Fibre channel technology.";
      }
      leaf-list sfp-plus-cable-technology {
        type enumeration {
          enum active-cable {
            description
              "Active Cable.";
            reference
              "SFF-8472 (Revision 12.4) Table 5-3 - Address A0h,
               Byte 8, bit 3";
          }
          enum passive-cable {
            description
              "Passive Cable.";
            reference
              "SFF-8472 (Revision 12.4) Table 5-3 - Address A0h,
               Byte 8, bit 2";
          }
        }
        config false;
        description
          "SFP+ cable technology.";
      }
      leaf-list fibre-channel-transmission-media {
        type enumeration {
          enum twin-axial-pair {
            description
              "Twin Axial Pair (TW).";
            reference
              "SFF-8472 (Revision 12.4) Table 5-3 - Address A0h,
               Byte 9, bit 7;
               SFF-8436 (Revision 4.9) Table 33 - Page 00h,
               Address 137, bit 7;
               SFF-8636 (Revision 2.11) Table 6-17 - Page 00h,
               Byte 137, bit 7";
          }
          enum twin-twisted-pair {
            description
              "Twin Twisted Pair (TP).";
            reference
              "SFF-8472 (Revision 12.4) Table 5-3 - Address A0h,
               Byte 9, bit 6;
               SFF-8436 (Revision 4.9) Table 33 - Page 00h,
               Address 137, bit 6;
               SFF-8636 (Revision 2.11) Table 6-17 - Page 00h,
               Byte 137, bit 6";
          }
          enum miniature-coax {
            description
              "Miniature Coax (MI).";
            reference
              "SFF-8472 (Revision 12.4) Table 5-3 - Address A0h,
               Byte 9, bit 5;
               SFF-8436 (Revision 4.9) Table 33 - Page 00h,
               Address 137, bit 5;
               SFF-8636 (Revision 2.11) Table 6-17 - Page 00h,
               Byte 137, bit 5";
          }
          enum video-coax {
            description
              "Video Coax (TV).";
            reference
              "SFF-8472 (Revision 12.4) Table 5-3 - Address A0h,
               Byte 9, bit 4;
               SFF-8436 (Revision 4.9) Table 33 - Page 00h,
               Address 137, bit 4;
               SFF-8636 (Revision 2.11) Table 6-17 - Page 00h,
               Byte 137, bit 4";
          }
          enum multimode-62.5um {
            description
              "Multimode, 62.5um (M6).";
            reference
              "SFF-8472 (Revision 12.4) Table 5-3 - Address A0h,
               Byte 9, bit 3;
               SFF-8436 (Revision 4.9) Table 33 - Page 00h,
               Address 137, bit 3;
               SFF-8636 (Revision 2.11) Table 6-17 - Page 00h,
               Byte 137, bit 3";
          }
          enum multimode-50um {
            description
              "Multimode, 50um (M5 or M5E).";
            reference
              "SFF-8472 (Revision 12.4) Table 5-3 - Address A0h,
               Byte 9, bit 2;
               SFF-8436 (Revision 4.9) Table 33 - Page 00h,
               Address 137, bit 2;
               SFF-8636 (Revision 2.11) Table 6-17 - Page 00h,
               Byte 137, bit 2";
          }
          enum multimode-50um-om3 {
            description
              "Multimode, 50um (OM3).";
            reference
              "SFF-8436 (Revision 4.9) Table 33 - Page 00h,
               Address 137, bit 1;
               SFF-8636 (Revision 2.11) Table 6-17 - Page 00h,
               Byte 137, bit 1";
          }
          enum single-mode {
            description
              "Single Mode (SM).";
            reference
              "SFF-8472 (Revision 12.4) Table 5-3 - Address A0h,
               Byte 9, bit 0;
               SFF-8436 (Revision 4.9) Table 33 - Page 00h,
               Address 137, bit 0;
               SFF-8636 (Revision 2.11) Table 6-17 - Page 00h,
               Byte 137, bit 0";
          }
        }
        config false;
        description
          "Fibre channel transmission media.";
      }
      leaf-list fibre-channel-speed {
        type enumeration {
          enum 1200-mbytes-sec {
            description
              "1200 MBytes/sec.";
            reference
              "SFF-8472 (Revision 12.4) Table 5-3 - Address A0h,
               Byte 10, bit 7;
               SFF-8436 (Revision 4.9) Table 33 - Page 00h,
               Address 138, bit 7;
               SFF-8636 (Revision 2.11) Table 6-17 - Page 00h,
               Byte 138, bit 7";
          }
          enum 800-mbytes-sec {
            description
              "800 MBytes/sec.";
            reference
              "SFF-8472 (Revision 12.4) Table 5-3 - Address A0h,
               Byte 10, bit 6;
               SFF-8436 (Revision 4.9) Table 33 - Page 00h,
               Address 138, bit 6;
               SFF-8636 (Revision 2.11) Table 6-17 - Page 00h,
               Byte 138, bit 6";
          }
          enum 1600-mbytes-sec {
            description
              "1600 MBytes/sec.";
            reference
              "SFF-8472 (Revision 12.4) Table 5-3 - Address A0h,
               Byte 10, bit 5;
               SFF-8436 (Revision 4.9) Table 33 - Page 00h,
               Address 138, bit 5;
               SFF-8636 (Revision 2.11) Table 6-17 - Page 00h,
               Byte 138, bit 5";
          }
          enum 400-mbytes-sec {
            description
              "400 MBytes/sec.";
            reference
              "SFF-8472 (Revision 12.4) Table 5-3 - Address A0h,
               Byte 10, bit 4;
               SFF-8436 (Revision 4.9) Table 33 - Page 00h,
               Address 138, bit 4;
               SFF-8636 (Revision 2.11) Table 6-17 - Page 00h,
               Byte 138, bit 4";
          }
          enum 3200-mbytes-sec {
            description
              "3200 MBytes/sec.";
            reference
              "SFF-8472 (Revision 12.4) Table 5-3 - Address A0h,
               Byte 10, bit 3;
               SFF-8636 (Revision 2.11) Table 6-17 - Page 00h,
               Byte 138, bit 3";
          }
          enum 200-mbytes-sec {
            description
              "200 MBytes/sec.";
            reference
              "SFF-8472 (Revision 12.4) Table 5-3 - Address A0h,
               Byte 10, bit 2;
               SFF-8436 (Revision 4.9) Table 33 - Page 00h,
               Address 138, bit 2
               SFF-8636 (Revision 2.11) Table 6-17 - Page 00h,
               Byte 138, bit 2";
          }
          enum 100-mbytes-sec {
            description
              "100 MBytes/sec.";
            reference
              "SFF-8472 (Revision 12.4) Table 5-3 - Address A0h,
               Byte 10, bit 0;
               SFF-8436 (Revision 4.9) Table 33 - Page 00h,
               Address 138, bit 0;
               SFF-8636 (Revision 2.11) Table 6-17 - Page 00h,
               Byte 138, bit 0";
          }
        }
        config false;
        description
          "Fibre channel speed (FCS).";
      }
      leaf-list fibre-channel-speed-2 {
        type enumeration {
          enum 64-gfc {
            description
              "64 GFC.";
            reference
              "SFF-8472 (Revision 12.4) Table 5-3 - Address A0h,
               Byte 62, bit 0";
          }
        }
        config false;
        description
          "Fibre channel speed 2 (FCS).";
      }
      leaf-list extended-specification {
        type enumeration {
          enum 100g-aoc-or-others-ber-5x10-5 {
            description
              "100G AOC (Active Optical Cable), retimed or 25GAUI C2M
               AOC. Providing a worst BER of 5 x 10^-5.";
            reference
              "SFF 8024 (Revision 4.12) Table 4-4 - Code 01h";
          }
          enum 100gbase-sr4-or-25gbase-sr {
            description
              "100GBASE-SR4 or 25GBASE-SR.";
            reference
              "SFF 8024 (Revision 4.12) Table 4-4 - Code 02h";
          }
          enum 100gbase-lr4-or-25gbase-lr {
            description
              "100GBASE-LR4 or 25GBASE-LR.";
            reference
              "SFF 8024 (Revision 4.12) Table 4-4 - Code 03h";
          }
          enum 100gbase-er4-or-25gbase-er {
            description
              "100GBASE-ER4 or 25GBASE-ER.";
            reference
              "SFF 8024 (Revision 4.12) Table 4-4 - Code 04h";
          }
          enum 100gbase-sr10 {
            description
              "100GBASE-SR10.";
            reference
              "SFF 8024 (Revision 4.12) Table 4-4 - Code 05h";
          }
          enum 100g-cwdm4 {
            description
              "100G CWDM4.";
            reference
              "SFF 8024 (Revision 4.12) Table 4-4 - Code 06h";
          }
          enum 100g-psm4-parallel-smf {
            description
              "100G PSM4 Parallel SMF.";
            reference
              "SFF 8024 (Revision 4.12) Table 4-4 - Code 07h";
          }
          enum 100g-acc-or-others-ber-5x10-5 {
            description
              "100G ACC (Active Copper Cable), retimed or 25GAUI C2M
               ACC. Providing a worst BER of 5 x 10^-5.";
            reference
              "SFF 8024 (Revision 4.12) Table 4-4 - Code 08h";
          }
          enum 100gbase-cr4-or-others {
            description
              "100GBASE-CR4, 25GBASE-CR CA-25G-L or 50GBASE-CR2 with
               RS (Clause91) FEC.";
            reference
              "SFF 8024 (Revision 4.12) Table 4-4 - Code 0Bh";
          }
          enum 25gbase-cr-ca-25g-s-or-others {
            description
              "25GBASE-CR CA-25G-S or 50GBASE-CR2 with BASE-R (Clause
               74 Fire code) FEC.";
            reference
              "SFF 8024 (Revision 4.12) Table 4-4 - Code 0Ch";
          }
          enum 25gbase-cr-ca-25g-n-or-others {
            description
              "25GBASE-CR CA-25G-N or 50GBASE-CR2 with no FEC.";
            reference
              "SFF 8024 (Revision 4.12) Table 4-4 - Code 0Dh";
          }
          enum 10m-single-pair-ethernet {
            description
              "10 Mb/s Single Pair Ethernet (802.3cg, Clause 146/147,
               1000 m copper).";
            reference
              "SFF 8024 (Revision 4.12) Table 4-4 - Code 0Eh";
          }
          enum 40gbase-er4 {
            description
              "40GBASE-ER4.";
            reference
              "SFF 8024 (Revision 4.12) Table 4-4 - Code 10h";
          }
          enum 4x10gbase-sr {
            description
              "4 x 10GBASE-SR.";
            reference
              "SFF 8024 (Revision 4.12) Table 4-4 - Code 11h";
          }
          enum 40g-psm4-parallel-smf {
            description
              "40G PSM4 Parallel SMF.";
            reference
              "SFF 8024 (Revision 4.12) Table 4-4 - Code 12h";
          }
          enum g959.1-profile-p1i1-2d1 {
            description
              "G959.1 profile P1I1-2D1 (10709 MBd, 2km, 1310 nm SM).";
            reference
              "SFF 8024 (Revision 4.12) Table 4-4 - Code 13h";
          }
          enum g959.1-profile-p1s1-2d2 {
            description
              "G959.1 profile P1S1-2D2 (10709 MBd, 40km, 1550 nm
               SM).";
            reference
              "SFF 8024 (Revision 4.12) Table 4-4 - Code 14h";
          }
          enum g959.1-profile-p1l1-2d2 {
            description
              "G959.1 profile P1L1-2D2 (10709 MBd, 80km, 1550 nm
               SM).";
            reference
              "SFF 8024 (Revision 4.12) Table 4-4 - Code 15h";
          }
          enum 10gbase-t-sfi {
            description
              "10GBASE-T with SFI electrical interface.";
            reference
              "SFF 8024 (Revision 4.12) Table 4-4 - Code 16h";
          }
          enum 100g-clr4 {
            description
              "100G CLR4.";
            reference
              "SFF 8024 (Revision 4.12) Table 4-4 - Code 17h";
          }
          enum 100g-aoc-or-others-ber-1x10-12 {
            description
              "100G AOC, retimed or 25GAUI C2M AOC. Providing a worst
               BER of 10^-12 or below.";
            reference
              "SFF 8024 (Revision 4.12) Table 4-4 - Code 18h";
          }
          enum 100g-acc-or-others-ber-1x10-12 {
            description
              "100G ACC, retimed or 25GAUI C2M ACC. Providing a worst
               BER of 10^-12 or below.";
            reference
              "SFF 8024 (Revision 4.12) Table 4-4 - Code 19h";
          }
          enum 100ge-dwdm2 {
            description
              "100GE-DWDM2 (DWDM transceiver using 2 wavelengths on a
               1550 nm DWDM grid with a reach up to 80 km).";
            reference
              "SFF 8024 (Revision 4.12) Table 4-4 - Code 1Ah";
          }
          enum 100g-1550nm-wdm {
            description
              "100G 1550nm WDM (4 wavelengths).";
            reference
              "SFF 8024 (Revision 4.12) Table 4-4 - Code 1Bh";
          }
          enum 10gbase-t-sr {
            description
              "10GBASE-T Short Reach (30 meters).";
            reference
              "SFF 8024 (Revision 4.12) Table 4-4 - Code 1Ch";
          }
          enum 5gbase-t {
            description
              "5GBASE-T.";
            reference
              "SFF 8024 (Revision 4.12) Table 4-4 - Code 1Dh";
          }
          enum 2.5gbase-t {
            description
              "2.5GBASE-T.";
            reference
              "SFF 8024 (Revision 4.12) Table 4-4 - Code 1Eh";
          }
          enum 40g-swdm4 {
            description
              "40G SWDM4.";
            reference
              "SFF 8024 (Revision 4.12) Table 4-4 - Code 1Fh";
          }
          enum 100g-swdm4 {
            description
              "100G SWDM4.";
            reference
              "SFF 8024 (Revision 4.12) Table 4-4 - Code 20h";
          }
          enum 100g-pam4-bidi {
            description
              "100G PAM4 BiDi.";
            reference
              "SFF 8024 (Revision 4.12) Table 4-4 - Code 21h";
          }
          enum 10gbase-br {
            description
              "10GBASE-BR (Clause 158).";
            reference
              "SFF 8024 (Revision 4.12) Table 4-4 - Code 37h";
          }
          enum 25gbase-br {
            description
              "25GBASE-BR (Clause 159).";
            reference
              "SFF 8024 (Revision 4.12) Table 4-4 - Code 38h";
          }
          enum 50gbase-br {
            description
              "50GBASE-BR (Clause 160).";
            reference
              "SFF 8024 (Revision 4.12) Table 4-4 - Code 39h";
          }
          enum 4wdm-10-msa {
            description
              "4WDM-10 MSA (10km version of 100G CWDM4 with same
               RS(528,514) FEC in host system).";
            reference
              "SFF 8024 (Revision 4.12) Table 4-4 - Code 22h";
          }
          enum 4wdm-20-msa {
            description
              "4WDM-20 MSA (20km version of 100GBASE-LR4 with
               RS(528,514) FEC in host system).";
            reference
              "SFF 8024 (Revision 4.12) Table 4-4 - Code 23h";
          }
          enum 4wdm-40-msa {
            description
              "4WDM-40 MSA (40km reach with APD receiver and
               RS(528,514) FEC in host system).";
            reference
              "SFF 8024 (Revision 4.12) Table 4-4 - Code 24h";
          }
          enum 100gbase-dr-caui-4 {
            description
              "100GBASE-DR (Clause 140), CAUI-4 (no FEC).";
            reference
              "SFF 8024 (Revision 4.12) Table 4-4 - Code 25h";
          }
          enum 100g-fr-or-100gbase-fr1-caui-4 {
            description
              "100G-FR or 100GBASE-FR1 (Clause 140), CAUI-4 (no FEC on
               host interface).";
            reference
              "SFF 8024 (Revision 4.12) Table 4-4 - Code 26h";
          }
          enum 100g-lr-or-100gbase-lr1-caui-4 {
            description
              "100G-LR or 100GBASE-LR1 (Clause 140), CAUI-4 (no FEC on
               host interface).";
            reference
              "SFF 8024 (Revision 4.12) Table 4-4 - Code 27h";
          }
          enum 100gbase-sr1-caui-4 {
            description
              "100GBASE-SR1 (802.3, Clause 167), CAUI-4 (no FEC on
               host interface).";
            reference
              "SFF 8024 (Revision 4.12) Table 4-4 - Code 28h";
          }
          enum 100gbase-vr1-caui-4 {
            description
              "100GBASE-VR1 (802.3, Clause 167), CAUI-4 (no FEC on
               host interface).";
            reference
              "SFF 8024 (Revision 4.12) Table 4-4 - Code 3Ah";
          }
          enum 100gbase-sr1-or-others {
            description
              "100GBASE-SR1, 200GBASE-SR2 or 400GBASE-SR4 (802.3,
               Clause 167).";
            reference
              "SFF 8024 (Revision 4.12) Table 4-4 - Code 29h";
          }
          enum 100gbase-vr1-or-others {
            description
              "100GBASE-VR1, 200GBASE-VR2 or 400GBASE-VR4 (802.3,
               Clause 167).";
            reference
              "SFF 8024 (Revision 4.12) Table 4-4 - Code 36h";
          }
          enum 100gbase-fr1-or-400gbase-dr4-2 {
            description
              "100GBASE-FR1 (802.3, Clause 140) or 400GBASE-DR4-2
               (P802.3df, Clause 124).";
            reference
              "SFF 8024 (Revision 4.12) Table 4-4 - Code 2Ah";
          }
          enum 100gbase-lr1 {
            description
              "100GBASE-LR1 (802.3, Clause 140).";
            reference
              "SFF 8024 (Revision 4.12) Table 4-4 - Code 2Bh";
          }
          enum 100g-lr1-20-msa-caui-4 {
            description
              "100G-LR1-20 MSA, CAUI-4 (no FEC on host interface).";
            reference
              "SFF 8024 (Revision 4.12) Table 4-4 - Code 2Ch";
          }
          enum 100g-er1-30-msa-caui-4 {
            description
              "100G-ER1-30 MSA, CAUI-4 (no FEC on host interface).";
            reference
              "SFF 8024 (Revision 4.12) Table 4-4 - Code 2Dh";
          }
          enum 100g-er1-40-msa-caui-4 {
            description
              "100G-ER1-40 MSA, CAUI-4 (no FEC on host interface).";
            reference
              "SFF 8024 (Revision 4.12) Table 4-4 - Code 2Eh";
          }
          enum 100g-lr1-20-msa {
            description
              "100G-LR1-20 MSA.";
            reference
              "SFF 8024 (Revision 4.12) Table 4-4 - Code 2Fh";
          }
          enum 100g-er1-30-msa {
            description
              "100G-ER1-30 MSA.";
            reference
              "SFF 8024 (Revision 4.12) Table 4-4 - Code 34h";
          }
          enum 100g-er1-40-msa {
            description
              "100G-ER1-40 MSA.";
            reference
              "SFF 8024 (Revision 4.12) Table 4-4 - Code 35h";
          }
          enum acc-50gaui-or-others-ber-1x10-6 {
            description
              "Active Copper Cable with 50GAUI, 100GAUI-2 or 200GAUI-4
               C2M. Providing a worst BER of 10^-6 or below.";
            reference
              "SFF 8024 (Revision 4.12) Table 4-4 - Code 30h";
          }
          enum aoc-50gaui-or-others-ber-1x10-6 {
            description
              "Active Optical Cable with 50GAUI, 100GAUI-2 or
               200GAUI-4 C2M. Providing a worst BER of 10^-6 or
               below.";
            reference
              "SFF 8024 (Revision 4.12) Table 4-4 - Code 31h";
          }
          enum acc-50gaui-or-others-mixed-ber {
            description
              "Active Copper Cable with 50GAUI, 100GAUI-2 or 200GAUI-4
               C2M. Providing a worst BER of 2.6x10^-4 for ACC, 10^-5
               for AUI, or below.";
            reference
              "SFF 8024 (Revision 4.12) Table 4-4 - Code 32h";
          }
          enum aoc-50gaui-or-others-mixed-ber {
            description
              "Active Optical Cable with 50GAUI, 100GAUI-2 or
               200GAUI-4 C2M. Providing a worst BER of 2.6x10^-4 for
               ACC, 10^-5 for AUI, or below.";
            reference
              "SFF 8024 (Revision 4.12) Table 4-4 - Code 33h";
          }
          enum 100gbase-cr1-or-others {
            description
              "100GBASE-CR1, 200GBASE-CR2 or 400GBASE-CR4 (P802.3ck,
               Clause 162).";
            reference
              "SFF 8024 (Revision 4.12) Table 4-4 - Code 3Fh";
          }
          enum 50gbase-cr-or-others {
            description
              "50GBASE-CR, 100GBASE-CR2, or 200GBASE-CR4.";
            reference
              "SFF 8024 (Revision 4.12) Table 4-4 - Code 40h";
          }
          enum 50gbase-sr-or-others {
            description
              "50GBASE-SR, 100GBASE-SR2, or 200GBASE-SR4.";
            reference
              "SFF 8024 (Revision 4.12) Table 4-4 - Code 41h";
          }
          enum 50gbase-fr-or-200gbase-dr4 {
            description
              "50GBASE-FR or 200GBASE-DR4.";
            reference
              "SFF 8024 (Revision 4.12) Table 4-4 - Code 42h";
          }
          enum 50gbase-er {
            description
              "50GBASE-ER (IEEE 802.3, Clause 139).";
            reference
              "SFF 8024 (Revision 4.12) Table 4-4 - Code 4Ah";
          }
          enum 200gbase-fr4 {
            description
              "200GBASE-FR4.";
            reference
              "SFF 8024 (Revision 4.12) Table 4-4 - Code 43h";
          }
          enum 200g-1550nm-psm4 {
            description
              "200G 1550 nm PSM4.";
            reference
              "SFF 8024 (Revision 4.12) Table 4-4 - Code 44h";
          }
          enum 50gbase-lr {
            description
              "50GBASE-LR.";
            reference
              "SFF 8024 (Revision 4.12) Table 4-4 - Code 45h";
          }
          enum 200gbase-lr4 {
            description
              "200GBASE-LR4.";
            reference
              "SFF 8024 (Revision 4.12) Table 4-4 - Code 46h";
          }
          enum 400gbase-dr4-or-400gaui-4-c2m {
            description
              "400GBASE-DR4 (802.3, Clause 124), 400GAUI-4 C2M (Annex
               120G).";
            reference
              "SFF 8024 (Revision 4.12) Table 4-4 - Code 47h";
          }
          enum 400gbase-fr4 {
            description
              "400GBASE-FR4 (802.3, Clause 151).";
            reference
              "SFF 8024 (Revision 4.12) Table 4-4 - Code 48h";
          }
          enum 400gbase-lr4-6 {
            description
              "400GBASE-LR4-6 (802.3, Clause 151).";
            reference
              "SFF 8024 (Revision 4.12) Table 4-4 - Code 49h";
          }
          enum 400g-lr4-10 {
            description
              "400G-LR4-10.";
            reference
              "SFF 8024 (Revision 4.12) Table 4-4 - Code 4Bh";
          }
          enum 400gbase-zr {
            description
              "400GBASE-ZR (P802.3cw, Clause 156).";
            reference
              "SFF 8024 (Revision 4.12) Table 4-4 - Code 4Ch";
          }
          enum 256gfc-sw4 {
            description
              "256GFC-SW4 (FC-PI-7P).";
            reference
              "SFF 8024 (Revision 4.12) Table 4-4 - Code 7Fh";
          }
          enum 64gfc {
            description
              "64GFC (FC-PI-7).";
            reference
              "SFF 8024 (Revision 4.12) Table 4-4 - Code 80h";
          }
          enum 128gfc {
            description
              "128GFC (FC-PI-8).";
            reference
              "SFF 8024 (Revision 4.12) Table 4-4 - Code 81h";
          }
        }
        config false;
        description
          "Extended specification compliance codes.";
        reference
          "SFF 8024 (Revision 4.12) Section 4.5";
      }
    }
  }

  grouping identifiers-and-codes {
    description
      "Identifiers and codes specific to a given transceiver.";
    container identifiers-and-codes {
      description
        "Identifiers and codes specific to a given transceiver.";
      reference
        "SFF-8472 (Revision 12.4) Section 5";
      leaf physical-device {
        type identityref {
          base physical-device;
        }
        config false;
        description
          "The identifier value specifies the physical device
           described by two-wire interface information.";
        reference
          "SFF-8472 (Revision 12.4) Table 5-1 - Address A0h, Byte 0";
      }
      leaf physical-device-extended-identifier {
        type enumeration {
          enum not-specified {
            description
              "GBIC definition is not specified or the GBIC definition
               is not compliant with a defined MOD_DEF.";
            reference
              "SFF-8472 (Revision 12.4) Table 5-2 - Address A0h,
               Byte 1, Value 00h";
          }
          enum mod-def1 {
            description
              "GBIC is compliant with MOD_DEF 1.";
            reference
              "SFF-8472 (Revision 12.4) Table 5-2 - Address A0h,
               Byte 1, Value 01h";
          }
          enum mod-def2 {
            description
              "GBIC is compliant with MOD_DEF 2.";
            reference
              "SFF-8472 (Revision 12.4) Table 5-2 - Address A0h,
               Byte 1, Value 02h";
          }
          enum mod-def3 {
            description
              "GBIC is compliant with MOD_DEF 3.";
            reference
              "SFF-8472 (Revision 12.4) Table 5-2 - Address A0h,
               Byte 1, Value 03h";
          }
          enum two-wire-interface-id {
            description
              "GBIC/SFP function is defined by two-wire interface ID
               only.";
            reference
              "SFF-8472 (Revision 12.4) Table 5-2 - Address A0h,
               Byte 1, Value 04h";
          }
          enum mod-def5 {
            description
              "GBIC is compliant with MOD_DEF 5.";
            reference
              "SFF-8472 (Revision 12.4) Table 5-2 - Address A0h,
               Byte 1, Value 05h";
          }
          enum mod-def6 {
            description
              "GBIC is compliant with MOD_DEF 6.";
            reference
              "SFF-8472 (Revision 12.4) Table 5-2 - Address A0h,
               Byte 1, Value 06h";
          }
          enum mod-def7 {
            description
              "GBIC is compliant with MOD_DEF 7.";
            reference
              "SFF-8472 (Revision 12.4) Table 5-2 - Address A0h,
               Byte 1, Value 07h";
          }
        }
        config false;
        description
          "The extended identifier value provides additional
           information about the transceiver. The field should be set
           to 'two-wire-interface-id' for all SFP modules indicating
           two-wire interface ID module definition. In many cases, a
           GBIC elects to use MOD_DEF 4 to make additional information
           about the GBIC available, even though the GBIC is actually
           compliant with one of the six other MOD_DEF values defined
           for GBICs. The extended identifier allows the GBIC to
           explicitly specify such compliance without requiring the
           MOD_DEF value to be inferred from the other information
           provided.";
        reference
          "SFF-8472 (Revision 12.4) Table 5-2 - Address A0h, Byte 1";
      }
      leaf connector {
        type identityref {
          base connector-type;
        }
        config false;
        description
          "Indicates the external optical or electrical cable
           connector provided as the media interface.";
        reference
          "SFF-8472 (Revision 12.4) Section 5.3 - Address A0h,
           Byte 2";
      }
      uses transceiver-compliance-codes;
      leaf encoding {
        type enumeration {
          enum unspecified {
            description
              "Unspecified encoding.";
            reference
              "SFF-8024 (Revision 4.12) Table 4-2 - Unspecified";
          }
          enum 8b-10b {
            description
              "8-bit words to 10-bit symbols (8B/10B).";
            reference
              "SFF-8024 (Revision 4.12) Table 4-2 - 8B/10B";
          }
          enum 4b-5b {
            description
              "4-bits to 5-bits (4B/5B).";
            reference
              "SFF-8024 (Revision 4.12) Table 4-2 - 4B/5B";
          }
          enum nrz {
            description
              "Non-return-to-zero (NRZ).";
            reference
              "SFF-8024 (Revision 4.12) Table 4-2 - NRZ";
          }
          enum manchester {
            description
              "Manchester encoding.";
            reference
              "SFF-8024 (Revision 4.12) Table 4-2 - Manchester";
          }
          enum sonet-scrambled {
            description
              "SONET scrambled.";
            reference
              "SFF-8024 (Revision 4.12) Table 4-2 - SONET Scrambled";
          }
          enum 64b-66b {
            description
              "64-bit data to 66-bit line code (64B/66B).";
            reference
              "SFF-8024 (Revision 4.12) Table 4-2 - 64B/66B";
          }
          enum 256b-257b {
            description
              "4 66 bit line code blocks to 257-bit block
               (256B/257B).";
            reference
              "SFF-8024 (Revision 4.12) Table 4-2 - 256B/257B
               (transcoded FEC-enabled data)";
          }
          enum pam4 {
            description
              "4-bit Pulse Amplitude Modulation (PAM4).";
            reference
              "SFF-8024 (Revision 4.12) Table 4-2 - PAM4";
          }
        }
        config false;
        description
          "The encoding value indicates the serial encoding mechanism
           that is the nominal design target of the particular
           transceiver. The value shall be contained in the two-wire
           interface data.";
        reference
          "SFF-8472 (Revision 12.4) Section 5.5 - Address A0h,
           Byte 11";
      }
      leaf nominal-bit-rate {
        type uint8;
        units "megabaud";
        config false;
        status deprecated;
        description
          "The nominal bit (signaling) rate (BR, nominal) is specified
           in units of megabaud (MBd). The bit rate includes those
           bits necessary to encode and delimit the signal as well as
           those bits carrying data information.

           For bit rates < 25.0 Gbps, the value will be reported in
           units of 100 MBd to the nearest 100 MBd.

           For bit rates >= 25.0 Gbps, the value will be reported in
           units of 250 MBd to the nearest 250 MBd.

           A value of 0 indicates that the bit rate is not specified
           and must be determined from the transceiver technology. The
           actual information transfer rate will depend on the
           encoding of the data, as defined by the encoding value.

           This leaf has been deprecated and replaced by
           'nominal-signaling-rate'.";
        reference
          "SFF-8472 (Revision 12.4) Table 5-6 - Address A0h, Byte 12;
           SFF-8472 (Revision 12.4) Section 8.4 - Address A0h,
           Byte 66";
      }
      leaf nominal-signaling-rate {
        type uint32;
        units "megabaud";
        config false;
        description
          "The nominal bit (signaling) rate (BR, nominal) is specified
           in units of megabaud (MBd). The bit rate includes those
           bits necessary to encode and delimit the signal as well as
           those bits carrying data information.

           For bit rates < 25.0 Gbps, the value will be reported to
           the nearest 100 MBd.

           For bit rates >= 25.0 Gbps, the value will be reported to
           the nearest 250 MBd.

           A value of 0 indicates that the bit rate is not specified
           and must be determined from the transceiver technology. The
           actual information transfer rate will depend on the
           encoding of the data, as defined by the encoding value.";
        reference
          "SFF-8472 (Revision 12.4) Table 5-6 - Address A0h, Byte 12;
           SFF-8472 (Revision 12.4) Section 8.4 - Address A0h,
           Byte 66";
      }
      leaf maximum-bit-rate {
        type bbf-yang:percent;
        config false;
        description
          "The upper bit rate limit above the nominal bit (signaling)
           rate at which the transceiver will still meet its
           specifications.";
        reference
          "SFF-8472 (Revision 12.4) Section 8.4 - Address A0h,
           Byte 66";
      }
      leaf minimum-bit-rate {
        type bbf-yang:percent;
        config false;
        description
          "The lower bit rate limit below the nominal bit (signaling)
           rate at which the transceiver will still meet its
           specifications.";
        reference
          "SFF-8472 (Revision 12.4) Section 8.5 - Address A0h,
           Byte 67";
      }
    }
  }

  grouping link-length {
    description
      "Nodes corresponding to link length.";
    container link-length {
      status deprecated;
      description
        "Link lengths for various modes of operation.";
      reference
        "SFF-8472 (Revision 12.4) Section 6";
      leaf length-single-mode-km {
        type uint8;
        units "kilometers";
        config false;
        status deprecated;
        description
          "This value specifies the link length that is supported by
           the transceiver while operating in compliance with the
           applicable standards using single mode fiber. The value is
           in units of kilometers. A value of 255 means that the
           transceiver supports a link length greater than 254
           kilometer (km). A value of zero means that the transceiver
           does not support single mode fiber or that the length
           information must be determined from the transceiver
           technology.";
        reference
          "SFF-8472 (Revision 12.4) Section 6.1 - Address A0h,
           Byte 14";
      }
      leaf length-single-mode-100m {
        type uint8;
        units "100 meters";
        config false;
        status deprecated;
        description
          "This value specifies the link length that is supported by
           the transceiver while operating in compliance with the
           applicable standards using single mode fiber. The value is
           in units of 100 meters. A value of 255 means that the
           transceiver supports a link length greater than 25.4 km. A
           value of zero means that the transceiver does not support
           single mode fiber or that the length information must be
           determined from the transceiver technology.";
        reference
          "SFF-8472 (Revision 12.4) Section 6.2 - Address A0h,
           Byte 15";
      }
      leaf length-50um-om2 {
        type uint8;
        units "10 meters";
        config false;
        status deprecated;
        description
          "This value specifies link length that is supported by the
           transceiver while operating in compliance with applicable
           standards using 50 micron multimode OM2 [500MHz*km at
           850nm] fiber. The value is in units of 10 meters. A value
           of 255 means that the transceiver supports a link length
           greater than 2.54 km. A value of zero means that the
           transceiver does not support 50 micron multimode fiber or
           that the length information must be determined from the
           transceiver technology.";
        reference
          "SFF-8472 (Revision 12.4) Section 6.3 - Address A0h,
           Byte 16";
      }
      leaf length-62.5um-om1 {
        type uint8;
        units "10 meters";
        config false;
        status deprecated;
        description
          "This value specifies link length that is supported by the
           transceiver while operating in compliance with applicable
           standards using 62.5 micron multimode OM1 [200 MHz*km at
           850nm, 500 MHz*km at 1310nm] fiber. The value is in units
           of 10 meters. A value of 255 means that the transceiver
           supports a link length greater than 2.54 km. A value of
           zero means that the transceiver does not support 62.5
           micron multimode fiber or that the length information must
           determined from the transceiver technology. It is common
           for a multimode transceiver to support OM1, OM2 and OM3
           fiber.";
        reference
          "SFF-8472 (Revision 12.4) Section 6.4 - Address A0h,
           Byte 17";
      }
      leaf length-62.5um-om2 {
        type uint8;
        units "10 meters";
        config false;
        status deprecated;
        description
          "This value specifies link length that is supported by the
           transceiver while operating in compliance with applicable
           standards using 62.5 micron multimode OM1 [200 MHz*km at
           850nm, 500 MHz*km at 1310nm] fiber. The value is in units
           of 10 meters. A value of 255 means that the transceiver
           supports a link length greater than 2.54 km. A value of
           zero means that the transceiver does not support 62.5
           micron multimode fiber or that the length information must
           determined from the transceiver technology. It is common
           for a multimode transceiver to support OM1, OM2 and OM3
           fiber.";
        reference
          "SFF-8472 (Revision 12.4) Section 6.4 - Address A0h,
           Byte 17";
      }
      leaf length-50um-om4 {
        type uint8;
        units "10 meters";
        config false;
        status deprecated;
        description
          "This value specifies link length that is
           supported by the transceiver while operating in compliance
           with applicable standards using 50 micron multimode OM4
           [4700 MHz*km] fiber. The value is in units of 10 meters. A
           value of 255 means that the transceiver supports a link
           length greater than 2.54 km. A value of zero means that the
           transceiver does not support 50 micron multimode fiber or
           that the length information must be determined from the
           transceiver codes.";
        reference
          "SFF-8472 (Revision 12.4) Section 6.5 - Address A0h,
           Byte 18";
      }
      leaf length-active-cable-or-copper {
        type uint8;
        units "meters";
        config false;
        status deprecated;
        description
          "This value specifies minimum link length supported by the
           transceiver while operating in compliance with applicable
           standards using copper cable. For active cable, this value
           represents actual length. The value is in units of 1 meter.
           A value of 255 means the transceiver supports a link length
           greater than 254 meters. A value of zero means the
           transceiver does not support copper or active cables or the
           length information must be determined from transceiver
           technology. Further information about cable design,
           equalization, and connectors is usually required to
           guarantee meeting a particular length requirement.";
        reference
          "SFF-8472 (Revision 12.4) Section 6.5 - Address A0h,
           Byte 18";
      }
      leaf length-50um-om3 {
        type uint8;
        units "10 meters";
        config false;
        status deprecated;
        description
          "This value specifies link length that is supported by the
           transceiver while operating in compliance with applicable
           standards using 50 micron multimode OM3 [2000 MHz*km]
           fiber. The value is in units of 10 meters. A value of 255
           means that the transceiver supports a link length greater
           than 2.54 km. A value of zero means that the transceiver
           does not support 50 micron multimode fiber or that the
           length information must be determined from the transceiver
           technology.";
        reference
          "SFF-8472 (Revision 12.4) Table 6-1 - Address A0h, Byte 19";
      }
    }
    container link-lengths {
      description
        "Link lengths for various modes of operation.";
      reference
        "SFF-8472 (Revision 12.4) Section 6;
         SFF-8436 (Revision 4.9) Section 7.6.2;
         SFF-8636 (Revision 2.11) Section 6.3";
      leaf length-single-mode {
        type union {
          type enumeration {
            enum technology-based-or-not-supported {
              description
                "Indicates that either single mode fiber is not
                 supported or the supported link length must be
                 determined from the transceiver technology.";
            }
            enum greater-than-254km {
              description
                "The supported link length is greater than 254
                 kilometers.";
              reference
                "SFF-8472 (Revision 12.4) Section 6.1";
            }
          }
          type uint32 {
            range "1..max";
          }
        }
        units "kilometers";
        config false;
        description
          "This value specifies the link length that is supported by
           the transceiver while operating in compliance with the
           applicable standards using single mode fiber.";
        reference
          "SFF-8472 (Revision 12.4) Section 6.1;
           SFF-8436 (Revision 4.9) Section 7.6.2.8;
           SFF-8636 (Revision 2.11) Section 6.3.8";
      }
      leaf length-single-mode-meters {
        type union {
          type enumeration {
            enum technology-based-or-not-supported {
              description
                "Indicates that either single mode fiber is not
                 supported or the supported link length must be
                 determined from the transceiver technology.";
            }
            enum greater-than-25400m {
              description
                "The supported link length is greater than 25400
                 meters.";
              reference
                "SFF-8472 (Revision 12.4) Section 6.2";
            }
          }
          type uint32 {
            range "1..max";
          }
        }
        units "meters";
        config false;
        description
          "This value specifies the link length that is supported by
           the transceiver while operating in compliance with the
           applicable standards using single mode fiber.";
        reference
          "SFF-8472 (Revision 12.4) Section 6.2";
      }
      leaf length-62.5um-om1 {
        type union {
          type enumeration {
            enum technology-based-or-not-supported {
              description
                "Indicates that either 62.5 micron multimode OM1 fiber
                 is not supported or the supported link length must be
                 determined from the transceiver technology.";
            }
            enum greater-than-2540m {
              description
                "The supported link length is greater than 2540
                 meters.";
              reference
                "SFF-8472 (Revision 12.4) Section 6.4";
            }
          }
          type uint32 {
            range "1..max";
          }
        }
        units "meters";
        config false;
        description
          "This value specifies link length that is supported by the
           transceiver while operating in compliance with applicable
           standards using 62.5 micron multimode OM1 [200 MHz*km at
           850 nm, 500 MHz*km at 1310 nm] fiber.";
        reference
          "SFF-8472 (Revision 12.4) Section 6.4;
           SFF-8436 (Revision 4.9) Section 7.6.2.11;
           SFF-8636 (Revision 2.11) Section 6.3.11";
      }
      leaf length-50um-om2 {
        type union {
          type enumeration {
            enum technology-based-or-not-supported {
              description
                "Indicates that either 50 micron multimode OM2 fiber
                 is not supported or the supported link length must be
                 determined from the transceiver technology.";
            }
            enum greater-than-2540m {
              description
                "The supported link length is greater than 2540
                 meters.";
              reference
                "SFF-8472 (Revision 12.4) Section 6.3";
            }
          }
          type uint32 {
            range "1..max";
          }
        }
        units "meters";
        config false;
        description
          "This value specifies link length that is supported by the
           transceiver while operating in compliance with applicable
           standards using 50 micron multimode OM2 [500 MHz*km at
           850 nm, 500 MHz*km at 1310 nm] fiber.";
        reference
          "SFF-8472 (Revision 12.4) Section 6.3;
           SFF-8436 (Revision 4.9) Section 7.6.2.10;
           SFF-8636 (Revision 2.11) Section 6.3.10";
      }
      leaf length-50um-om3 {
        type union {
          type enumeration {
            enum technology-based-or-not-supported {
              description
                "Indicates that either 50 micron multimode OM3 fiber
                 is not supported or the supported link length must be
                 determined from the transceiver technology.";
            }
            enum greater-than-2540m {
              description
                "The supported link length is greater than 2540
                 meters.";
              reference
                "SFF-8472 (Revision 12.4) Section 6.6";
            }
          }
          type uint32 {
            range "1..max";
          }
        }
        units "meters";
        config false;
        description
          "This value specifies link length that is supported by the
           transceiver while operating in compliance with applicable
           standards using 50 micron multimode OM3 [2000 MHz*km at
           850 nm] fiber.";
        reference
          "SFF-8472 (Revision 12.4) Section 6.6;
           SFF-8436 (Revision 4.9) Section 7.6.2.9;
           SFF-8636 (Revision 2.11) Section 6.3.9";
      }
      leaf length-50um-om4 {
        type union {
          type enumeration {
            enum technology-based-or-not-supported {
              description
                "Indicates that either 50 micron multimode OM4 fiber
                 is not supported or the supported link length must be
                 determined from the transceiver technology.";
            }
            enum greater-than-2540m {
              description
                "The supported link length is greater than 2540
                 meters.";
              reference
                "SFF-8472 (Revision 12.4) Section 6.5";
            }
            enum greater-than-508m {
              description
                "The supported link length is greater than 508
                 meters.";
              reference
                "SFF-8636 (Revision 2.11) Section 6.3.12";
            }
          }
          type uint32 {
            range "1..max";
          }
        }
        units "meters";
        config false;
        description
          "This value specifies link length that is supported by the
           transceiver while operating in compliance with applicable
           standards using 50 micron multimode OM4 [4700 MHz*km at
           850 nm] fiber.";
        reference
          "SFF-8472 (Revision 12.4) Section 6.5;
           SFF-8636 (Revision 2.11) Section 6.3.12";
      }
      leaf length-active-cable-or-copper {
        type union {
          type enumeration {
            enum technology-based-or-not-supported {
              description
                "Indicates that either the transceiver is not a cable
                 assembly or the supported link length must be
                 determined from the transceiver technology.";
            }
            enum greater-than-254m {
              description
                "The supported link length is greater than 254
                 meters.";
              reference
                "SFF-8472 (Revision 12.4) Section 6.6;
                 SFF-8436 (Revision 4.9) Section 7.6.2.12;
                 SFF-8636 (Revision 2.11) Section 6.3.12";
            }
          }
          type uint32 {
            range "1..max";
          }
        }
        units "meters";
        config false;
        description
          "This value specifies minimum link length supported by the
           transceiver while operating in compliance with applicable
           standards using copper cable. For active cable, this value
           represents actual length. Further information about cable
           design, equalization, and connectors is usually required to
           guarantee meeting a particular length requirement.";
        reference
          "SFF-8472 (Revision 12.4) Section 6.6;
           SFF-8436 (Revision 4.9) Section 7.6.2.12;
           SFF-8636 (Revision 2.11) Section 6.3.12";
      }
    }
  }

  grouping vendor-fields {
    description
      "Vendor-specific transceiver data.";
    container vendor-fields {
      description
        "Transceiver information relative to the vendor. SFF-8472
         sections 7.1 to 7.4, 8.6 and 8.7 define this data. The
         following are already defined in the base ietf-hardware
         model for each component regardless of class.

         7.1 Vendor Name
         The vendor name is a 16 character field that contains ASCII
         characters, left-aligned and padded on the right with ASCII
         spaces (20h). The vendor name shall be the full name of the
         corporation, a commonly accepted abbreviation of the name of
         the corporation, the SCSI company code for the corporation,
         or the stock exchange code for the corporation. At least one
         of the vendor name or the vendor OUI fields shall contain
         valid data.

         This is reported via 'mfg-name'.

         7.4 Vendor Rev
         The vendor revision number (vendor rev) is a 4-byte field
         that contains ASCII characters, left-aligned and padded on
         the right with ASCII spaces (20h), defining the Vendor's
         product revision number. An empty string indicates that the
         vendor revision is unspecified.

         This is reported via 'hardware-rev'.

         8.6 Vendor SN
         The vendor serial number (vendor SN) is a 16 character field
         that contains ASCII characters, left-aligned and padded on
         the right with ASCII spaces (20h), defining the Vendor's
         serial number for the transceiver. An empty string indicates
         that the vendor SN is unspecified.

         This is reported via 'serial-num'.

         8.7 Date Code
         The date code is an 8-byte field that contains the Vendor's
         date code in ASCII characters. The date code is mandatory.

         This is reported via 'mfg-date'.";
      reference
        "SFF-8472 (Revision 12.4) Section 7.1 - Address A0h,
         Bytes 20-35;
         SFF-8472 (Revision 12.4) Section 7.4 - Address A0h,
         Bytes 56-59;
         SFF-8472 (Revision 12.4) Section 8.6 - Address A0h,
         Bytes 68-83;
         SFF-8472 (Revision 12.4) Section 8.7 - Address A0h,
         Bytes 84-91;";
      leaf oui {
        type string {
          pattern '[0-9a-fA-F]{2}(:[0-9a-fA-F]{2}){2}';
        }
        config false;
        description
          "The vendor organizationally unique identifier field
           (Vendor OUI) is a 3-byte field that contains the IEEE
           Company Identifier for the vendor. A value of '00:00:00'
           indicates that the Vendor OUI is unspecified.";
        reference
          "SFF-8472 (Revision 12.4) Section 7.2 - Address A0h,
           Bytes 37-39";
      }
      leaf part-number {
        type string {
          pattern '[ -~]{0,16}';
        }
        config false;
        description
          "The vendor part number (vendor PN) is a 16-byte field that
           contains ASCII characters, left-aligned and padded on the
           right with ASCII spaces (20h), defining the vendor part
           number or product name. An empty string indicates that the
           vendor PN is unspecified.";
        reference
          "SFF-8472 (Revision 12.4) Section 7.3 - Address A0h,
           Bytes 40-55";
      }
      container eeprom {
        if-feature "bbf-hw-xcvr:vendor-eeprom";
        config false;
        description
          "Data nodes reporting the contents of the vendor-specific
           EEPROM data fields.";
        reference
          "SFF-8472 (Revision 12.4) Table 4-1 - Address A0h,
           Bytes 96-127;
           SFF-8436 (Revision 4.9) Table 29 - Page 00h,
           Addresses 224-255;
           INF-8077i (Revision 4.5) Table 46 - Page 01h,
           Addresses 224-255";
        leaf string {
          if-feature "bbf-hw-xcvr:vendor-eeprom-string";
          type string {
            length "0..32";
            pattern '[ -~]*';
          }
          description
            "Contents of the vendor-specific EEPROM locations as a
             sequence of an ASCII characters. Note that non-printable
             characters will be ignored.

             A zero length string indicates no octets are printable
             ASCII characters

             The binary representation provided by 'binary', if
             supported, will return all octets regardless of value.";
        }
        leaf binary {
          if-feature "bbf-hw-xcvr:vendor-eeprom-binary";
          type binary {
            length "0..32";
          }
          description
            "Contents of the vendor-specific EEPROM locations as a
             sequence of octets.";
        }
      }
    }
  }

  grouping common-thresholds {
    description
      "Transceiver and transceiver-link
       common thresholds parameters.";
    leaf tx-bias-high-alarm {
      type uint32;
      units "microamperes";
      config false;
      description
        "The bias current above which will trigger a high transmit
         bias alarm.";
      reference
        "SFF-8472 (Revision 12.4) Table 9-5 - Address A2h,
         Bytes 16-17";
    }
    leaf tx-bias-low-alarm {
      type uint32;
      units "microamperes";
      config false;
      description
        "The bias current below which will trigger a low transmit
         bias alarm.";
      reference
        "SFF-8472 (Revision 12.4) Table 9-5 - Address A2h,
         Bytes 18-19";
    }
    leaf tx-bias-high-warning {
      type uint32;
      units "microamperes";
      config false;
      description
        "The bias current above which will trigger a high transmit
         bias warning.";
      reference
        "SFF-8472 (Revision 12.4) Table 9-5 - Address A2h,
         Bytes 20-21";
    }
    leaf tx-bias-low-warning {
      type uint32;
      units "microamperes";
      config false;
      description
        "The bias current below which will trigger a low transmit
         bias warning.";
      reference
        "SFF-8472 (Revision 12.4) Table 9-5 - Address A2h,
         Bytes 22-23";
    }
    leaf tx-power-high-alarm {
      type uint32;
      units "0.1 microwatts";
      config false;
      description
        "The power above which will trigger a high transmit power
         alarm.";
      reference
        "SFF-8472 (Revision 12.4) Table 9-5 - Address A2h,
         Bytes 24-25";
    }
    leaf tx-power-low-alarm {
      type uint32;
      units "0.1 microwatts";
      config false;
      description
        "The power below which will trigger a low transmit power
         alarm.";
      reference
        "SFF-8472 (Revision 12.4) Table 9-5 - Address A2h,
         Bytes 26-27";
    }
    leaf tx-power-high-warning {
      type uint32;
      units "0.1 microwatts";
      config false;
      description
        "The power above which will trigger a high transmit power
         warning.";
      reference
        "SFF-8472 (Revision 12.4) Table 9-5 - Address A2h,
         Bytes 28-29";
    }
    leaf tx-power-low-warning {
      type uint32;
      units "0.1 microwatts";
      config false;
      description
        "The power below which will trigger a low transmit power
         warning.";
      reference
        "SFF-8472 (Revision 12.4) Table 9-5 - Address A2h,
         Bytes 30-31";
    }
    leaf rx-power-high-alarm {
      type uint32;
      units "0.1 microwatts";
      config false;
      description
        "The power above which will trigger a high receive power
         alarm.";
      reference
        "SFF-8472 (Revision 12.4) Table 9-5 - Address A2h,
         Bytes 32-33";
    }
    leaf rx-power-low-alarm {
      type uint32;
      units "0.1 microwatts";
      config false;
      description
        "The power below which will trigger a low receive power
         alarm.";
      reference
        "SFF-8472 (Revision 12.4) Table 9-5 - Address A2h,
         Bytes 34-35";
    }
    leaf rx-power-high-warning {
      type uint32;
      units "0.1 microwatts";
      config false;
      description
        "The power above which will trigger a high receive power
         warning.";
      reference
        "SFF-8472 (Revision 12.4) Table 9-5 - Address A2h,
         Bytes 36-37";
    }
    leaf rx-power-low-warning {
      type uint32;
      units "0.1 microwatts";
      config false;
      description
        "The power below which will trigger a low receive power
         warning.";
      reference
        "SFF-8472 (Revision 12.4) Table 9-5 - Address A2h,
         Bytes 38-39";
    }
    leaf tx-power-dbm-high-alarm {
      type power-dbm;
      config false;
      description
        "The power value above which will trigger a high transmit
         power alarm.";
      reference
        "SFF-8472 (Revision 12.4) Table 9-5 - Address A2h,
         Bytes 24-25";
    }
    leaf tx-power-dbm-low-alarm {
      type power-dbm;
      config false;
      description
        "The power value below which will trigger a low transmit
         power alarm.";
      reference
        "SFF-8472 (Revision 12.4) Table 9-5 - Address A2h,
         Bytes 26-27";
    }
    leaf tx-power-dbm-high-warning {
      type power-dbm;
      config false;
      description
        "The power value above which will trigger a high transmit
         power warning.";
      reference
        "SFF-8472 (Revision 12.4) Table 9-5 - Address A2h,
         Bytes 28-29";
    }
    leaf tx-power-dbm-low-warning {
      type power-dbm;
      config false;
      description
        "The power value below which will trigger a low transmit
         power warning.";
      reference
        "SFF-8472 (Revision 12.4) Table 9-5 - Address A2h,
         Bytes 30-31";
    }
    leaf rx-power-dbm-high-alarm {
      type power-dbm;
      config false;
      description
        "The power value above which will trigger a high receive
         power alarm.";
      reference
        "SFF-8472 (Revision 12.4) Table 9-5 - Address A2h,
         Bytes 32-33";
    }
    leaf rx-power-dbm-low-alarm {
      type power-dbm;
      config false;
      description
        "The power value below which will trigger a low receive
         power alarm.";
      reference
        "SFF-8472 (Revision 12.4) Table 9-5 - Address A2h,
         Bytes 34-35";
    }
    leaf rx-power-dbm-high-warning {
      type power-dbm;
      config false;
      description
        "The power value above which will trigger a high receive
         power warning.";
      reference
        "SFF-8472 (Revision 12.4) Table 9-5 - Address A2h,
         Bytes 36-37";
    }
    leaf rx-power-dbm-low-warning {
      type power-dbm;
      config false;
      description
        "The power value below which will trigger a low receive
         power warning.";
      reference
        "SFF-8472 (Revision 12.4) Table 9-5 - Address A2h,
         Bytes 38-39";
    }
    leaf laser-temperature-high-alarm {
      type int32;
      units "millidegrees Celsius";
      config false;
      description
        "The temperature above which will trigger a high laser
         temperature alarm.";
      reference
        "SFF-8472 (Revision 12.4) Table 9-5 - Address A2h,
         Bytes 40-41";
    }
    leaf laser-temperature-low-alarm {
      type int32;
      units "millidegrees Celsius";
      config false;
      description
        "The temperature below which will trigger a low laser
         temperature alarm.";
      reference
        "SFF-8472 (Revision 12.4) Table 9-5 - Address A2h,
         Bytes 42-43";
    }
    leaf laser-temperature-high-warning {
      type int32;
      units "millidegrees Celsius";
      config false;
      description
        "The temperature above which will trigger a high laser
         temperature warning.";
      reference
        "SFF-8472 (Revision 12.4) Table 9-5 - Address A2h,
         Bytes 44-45";
    }
    leaf laser-temperature-low-warning {
      type int32;
      units "millidegrees Celsius";
      config false;
      description
        "The temperature below which will trigger a low laser
         temperature warning.";
      reference
        "SFF-8472 (Revision 12.4) Table 9-5 - Address A2h,
         Bytes 46-47";
    }
    leaf tec-current-high-alarm {
      type int16;
      units "0.1 milliamperes";
      config false;
      description
        "The current above which will trigger a high Thermoelectric
         Cooler (TEC) current alarm.";
      reference
        "SFF-8472 (Revision 12.4) Table 9-5 - Address A2h,
         Bytes 48-49";
    }
    leaf tec-current-low-alarm {
      type int16;
      units "0.1 milliamperes";
      config false;
      description
        "The current below which will trigger a low Thermoelectric
         Cooler (TEC) current alarm.";
      reference
        "SFF-8472 (Revision 12.4) Table 9-5 - Address A2h,
         Bytes 50-51";
    }
    leaf tec-current-high-warning {
      type int16;
      units "0.1 milliamperes";
      config false;
      description
        "The current above which will trigger a high Thermoelectric
         Cooler (TEC) current warning.";
      reference
        "SFF-8472 (Revision 12.4) Table 9-5 - Address A2h,
         Bytes 52-53";
    }
    leaf tec-current-low-warning {
      type int16;
      units "0.1 milliamperes";
      config false;
      description
        "The current below which will trigger a low Thermoelectric
         Cooler (TEC) current warning.";
      reference
        "SFF-8472 (Revision 12.4) Table 9-5 - Address A2h,
         Bytes 54-55";
    }
  }

  grouping thresholds {
    description
      "Transceiver thresholds.";
    container thresholds {
      description
        "Each diagnostic value has a corresponding high alarm, low
         alarm, high warning and low warning threshold. These factory
         preset values allow the user to determine when a particular
         value is outside of 'normal' limits as determined by the
         transceiver manufacturer. It is assumed that these values
         will vary with different technologies and different
         implementations. When external calibration is used, data may
         be compared to alarm and warning threshold values before or
         after calibration by the host. Comparison can be done
         directly before calibration. If comparison is to be done
         after calibration, calibration must first be applied to both
         data and threshold values.

         The values reported in the alarm and warning thresholds area
         (see below) may be temperature compensated or otherwise
         adjusted when setting warning and/or alarm flags. Any
         threshold compensation or adjustment is vendor-specific and
         optional.";
      reference
        "SFF-8472 (Revision 12.4) Table 9-5 - Address A2h,
         Bytes 0-39";
      leaf temperature-high-alarm {
        type int32;
        units "millidegrees Celsius";
        config false;
        description
          "The temperature above which will trigger a high temperature
           alarm.";
        reference
          "SFF-8472 (Revision 12.4) Table 9-5 - Address A2h,
           Bytes 00-01";
      }
      leaf temperature-low-alarm {
        type int32;
        units "millidegrees Celsius";
        config false;
        description
          "The temperature below which will trigger a low temperature
           alarm.";
        reference
          "SFF-8472 (Revision 12.4) Table 9-5 - Address A2h,
           Bytes 02-03";
      }
      leaf temperature-high-warning {
        type int32;
        units "millidegrees Celsius";
        config false;
        description
          "The temperature above which will trigger a high temperature
           warning.";
        reference
          "SFF-8472 (Revision 12.4) Table 9-5 - Address A2h,
           Bytes 04-05";
      }
      leaf temperature-low-warning {
        type int32;
        units "millidegrees Celsius";
        config false;
        description
          "The temperature below which will trigger a low temperature
           warning.";
        reference
          "SFF-8472 (Revision 12.4) Table 9-5 - Address A2h,
           Bytes 06-07";
      }
      leaf supply-voltage-high-alarm {
        type uint16;
        units "0.1 millivolts";
        config false;
        description
          "The voltage above which will trigger a high supply voltage
           alarm.";
        reference
          "SFF-8472 (Revision 12.4) Table 9-5 - Address A2h,
           Bytes 08-09";
      }
      leaf supply-voltage-low-alarm {
        type uint16;
        units "0.1 millivolts";
        config false;
        description
          "The voltage below which will trigger a low supply voltage
           alarm.";
        reference
          "SFF-8472 (Revision 12.4) Table 9-5 - Address A2h,
           Bytes 10-11";
      }
      leaf supply-voltage-high-warning {
        type uint16;
        units "0.1 millivolts";
        config false;
        description
          "The voltage above which will trigger a high supply voltage
           warning.";
        reference
          "SFF-8472 (Revision 12.4) Table 9-5 - Address A2h,
           Bytes 12-13";
      }
      leaf supply-voltage-low-warning {
        type uint16;
        units "0.1 millivolts";
        config false;
        description
          "The voltage below which will trigger a low supply voltage
           warning.";
        reference
          "SFF-8472 (Revision 12.4) Table 9-5 - Address A2h,
           Bytes 14-15";
      }
      uses common-thresholds;
    }
  }

  grouping transceiver-link-thresholds {
    description
      "Transceiver-link thresholds.";
    container thresholds {
      description
        "Each diagnostic value has a corresponding high alarm, low
         alarm, high warning and low warning threshold. These factory
         preset values allow the user to determine when a particular
         value is outside of 'normal' limits as determined by the
         transceiver manufacturer. It is assumed that these values
         will vary with different technologies and different
         implementations. When external calibration is used, data may
         be compared to alarm and warning threshold values before or
         after calibration by the host. Comparison can be done
         directly before calibration. If comparison is to be done
         after calibration, calibration must first be applied to both
         data and threshold values.

         The values reported in the alarm and warning thresholds area
         (see below) may be temperature compensated or otherwise
         adjusted when setting warning and/or alarm flags. Any
         threshold compensation or adjustment is vendor-specific and
         optional.";
      reference
        "SFF-8472 (Revision 12.4) Table 9-5 - Address A2h,
         Bytes 16-39";
      uses common-thresholds;
    }
  }

  grouping extended-information {
    description
      "Data nodes related to the extended information data fields of
       the pluggable module.";
    container extended-information {
      if-feature "bbf-hw-xcvr:extended-information";
      config false;
      description
        "Data nodes related to the extended information of the
         pluggable module.";
      reference
        "SFF-8472 (Revision 12.4) Section 10";
      container user-eeprom {
        if-feature "bbf-hw-xcvr:user-eeprom";
        description
          "Data nodes reporting the contents of the user-writable
           EEPROM data fields.";
        reference
          "SFF-8472 (Revision 12.4) Table 10-4 - Address A2h,
           Page 00h/01h, Bytes 128-247;
           SFF-8436 (Revision 4.9) Section 7.6.4;
           INF-8077i (Revision 4.5) Section 5.45";
        leaf string {
          if-feature "bbf-hw-xcvr:user-eeprom-string";
          type string {
            length "0..128";
            pattern '[ -~]*';
          }
          description
            "Content of the user-writable EEPROM locations, excluding
             the Common Language Equipment Identifier (CLEI) code, if
             any, represented as a sequence of ASCII characters.

             Note, the CLEI code, if any, is provided in the
             hardware's component leaf 'uri'.

             Note that non-printable characters will be ignored. A
             zero length string indicates no octets are printable
             ASCII characters.

             The binary representation provided by 'binary', if
             supported, will return all octets regardless of value.";
        }
        leaf binary {
          if-feature "bbf-hw-xcvr:user-eeprom-binary";
          type binary {
            length "0..128";
          }
          description
            "Content of the user-writable EEPROM locations, excluding
             the Common Language Equipment Identifier (CLEI) code, if
             any, represented as a sequence of octets.

             Note, the CLEI code, if any, is provided in the
             hardware's component leaf 'uri'.";
        }
      }
    }
  }

  augment "/hw:hardware/hw:component" {
    when "derived-from-or-self(hw:class,'bbf-hwt:transceiver')";
    description
      "Data nodes for hardware components of identity class
       'transceiver'.";
    container transceiver {
      description
        "Data nodes for hardware components of identity class
         'transceiver'.";
      uses identifiers-and-codes;
      uses link-length;
      uses vendor-fields;
      leaf diagnostics-monitoring-type {
        type bits {
          bit legacy {
            description
              "Legacy diagnostic implementation.";
            reference
              "SFF-8472 (Revision 12.4) Table 8-5 - Address A0h,
               Byte 92, bit 7";
          }
        }
        config false;
        description
          "Describes how diagnostic monitoring is implemented in the
           particular transceiver.";
        reference
          "SFF-8472 (Revision 12.4) Section 8.8 - Address A0h,
           Byte 92";
      }
      leaf enhanced-options {
        type bits {
          bit alarm-warning-flags {
            description
              "Optional Alarm/warning flags implemented for all
               monitored quantities (see Table 9-12).";
            reference
              "SFF-8472 (Revision 12.4) Table 8-6 - Address A0h,
               Byte 93, bit 7";
          }
          bit soft-tx-disable {
            description
              "Optional soft TX_DISABLE control and monitoring
               implemented.";
            reference
              "SFF-8472 (Revision 12.4) Table 8-6 - Address A0h,
               Byte 93, bit 6";
          }
          bit soft-tx-fault {
            description
              "Optional soft TX_FAULT monitoring implemented.";
            reference
              "SFF-8472 (Revision 12.4) Table 8-6 - Address A0h,
               Byte 93, bit 5";
          }
          bit soft-rx-los {
            description
              "Optional soft RX_LOS monitoring implemented.";
            reference
              "SFF-8472 (Revision 12.4) Table 8-6 - Address A0h,
               Byte 93, bit 4";
          }
          bit soft-rate-select {
            description
              "Optional soft RATE_SELECT control and monitoring
               implemented.";
            reference
              "SFF-8472 (Revision 12.4) Table 8-6 - Address A0h,
               Byte 93, bit 3";
          }
          bit application-select {
            description
              "Optional Application Select control implemented per
               SFF-8079.";
            reference
              "SFF-8079;
               SFF-8472 (Revision 12.4) Table 8-6 - Address A0h,
               Byte 93, bit 2";
          }
          bit alarm-rate-select-sff-8431 {
            description
              "Optional soft Rate Select control implemented per
               SFF-8431.";
            reference
              "SFF-8431;
               SFF-8472 (Revision 12.4) Table 8-6 - Address A0h,
               Byte 93, bit 1";
          }
        }
        config false;
        description
          "The Enhanced Options are indicators which describe the
           optional digital diagnostic features implemented in the
           transceiver. Since transceivers will not necessarily
           implement all optional features, this field allows the host
           system to determine which functions are available over the
           2 wire serial bus.";
        reference
          "SFF-8472 (Revision 12.4) Table 8-6 - Address A0h, Byte 93";
      }
      container diagnostics {
        presence
          "If present, indicates that digital diagnostics monitoring
           has been implemented in the transceiver. Supply voltage
           monitoring and temperature monitoring must both be
           implemented.";
        description
          "Diagnostic data of the transceiver.";
        reference
          "SFF-8472 (Revision 12.4) Section 8.8 - Address A0h,
           Byte 92;
           SFF-8472 (Revision 12.4) Section 9";
        uses transceiver-diagnostic-parameters;
        uses transceiver-alarm-diagnostic-parameters;
      }
      uses thresholds;
      uses extended-information;
      container module-power {
        description
          "Data nodes related to the module power.";
        leaf power-class {
          type identityref {
            base power-class;
          }
          config false;
          description
            "The form factor specific classification of the maximum
             power.";
          reference
            "SFF-8472 (Revision 12.4) Table 8-3 - Address A0h,
             Byte 64, Bits 6, 5 and 1;
             SFF-8436 (Revision 4.9) Table 31;
             SFF-8636 (Revision 2.11) Table 6-16 - Page 00h,
             Byte 129, Bits 7, 6, 5, 1, and 0";
        }
        leaf maximum-power {
          type decimal64 {
            fraction-digits 2;
          }
          units "Watts";
          config false;
          description
            "The maximum power consumption of the transceiver. If this
             value is not present, the maximum power consumption is
             solely determined by the power class.";
          reference
            "SFF-8636 (Revision 2.11) Section 6.2.9 - Page 00h,
             Byte 107";
        }
      }
    }
  }

  augment "/hw:hardware/hw:component" {
    when "derived-from-or-self(hw:class,'bbf-hwt:transceiver-link')";
    description
      "Data nodes for hardware components of identity class
       'transceiver-link'.";
    container transceiver-link {
      description
        "Data nodes for hardware components of identity class
         'transceiver-link'.";
      uses link-parameters;
      container diagnostics {
        presence
          "If present, indicates that digital diagnostics monitoring
           has been implemented in the transceiver. Received power
           monitoring, transmit power monitoring and bias current
           monitoring must all be implemented.";
        description
          "Diagnostic data of the transceiver link.";
        reference
          "SFF-8472 (Revision 12.4) Section 8.8 - Address A0h,
           Byte 92;
           SFF-8472 (Revision 12.4) Section 9";
        uses link-diagnostic-parameters;
        uses link-alarm-diagnostic-parameters;
      }
      uses transceiver-link-thresholds;
    }
  }
}
