submodule bbf-hardware-rpf-dpu-config {
  yang-version 1.1;
  belongs-to bbf-hardware-rpf-dpu {
    prefix bbf-hw-rpf-dpu;
  }

  import ietf-inet-types {
    prefix inet;
  }

  include bbf-hardware-rpf-dpu-performance;

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for 
     the configuration of Reverse Power Feeding (RPF) for a 
     Distribution Point Unit (DPU).

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }

  identity rpf-threshold-crossing-alert {
    description
      "Base identity for RPF threshold crossing alerts (TCA).

       This identity is abstract and is not be used for a 
       threshold crossing alert.";
  }

  identity rpf-15min-threshold-crossing-alert {
    base rpf-threshold-crossing-alert;
    description
      "A threshold crossing alert associated with performance  
       counters collected over the current 15 minute interval
       for RPF.

       This identity is abstract and is not be used for a 
       threshold crossing alert.";
  }

  identity rpf-24hr-threshold-crossing-alert {
    base rpf-threshold-crossing-alert;
    description
      "A threshold crossing alert associated with performance  
       counters collected over the current 24 hour interval
       for RFP.

       This identity is abstract and is not be used for a 
       threshold crossing alert.";
  }

  identity dpu-15min-extracted-energy-tca {
    base rpf-15min-threshold-crossing-alert;
    description
      "The count of the DPU extracted energy per line at U-O interface
       or at PSU input in the current 15 minute interval has exceeded
       the configured threshold.";
    reference
      "ITU-T G.997.2 clause A.7.3.4 (CURR/PREV_NE_15/24_EE)";
  }

  identity dpu-24hr-extracted-energy-tca {
    base rpf-24hr-threshold-crossing-alert;
    description
      "The count of the DPU extracted energy per line at U-O interface
       or at PSU input in the current 24 hour interval has exceeded
       the configured threshold.";
    reference
      "ITU-T G.997.2 clause A.7.3.4 (CURR/PREV_NE_15/24_EE)";
  }

  identity pse-15min-injected-energy-tca {
    base rpf-15min-threshold-crossing-alert;
    description
      "The count of the PSE injected energy per line in the current 
       15 minute interval has exceeded the configured threshold.";
    reference
      "ITU-T G.997.2 clause A.7.3.5 (CURR/PREV_FE_15/24_IE)";
  }

  identity pse-24hr-injected-energy-tca {
    base rpf-24hr-threshold-crossing-alert;
    description
      "The count of the PSE injected energy per line in the current 
       24 hour interval has exceeded the configured threshold.";
    reference
      "ITU-T G.997.2 clause A.7.3.5 (CURR/PREV_FE_15/24_IE)";
  }

  grouping rpf-near-end-system-config {
    description
      "RPF near-end system level configuration.";

    leaf dying-gasp-udp-port {
      type inet:port-number;
      description
        "The UDP port number used for dying gasp messages.";
      reference
        "BBF TR-301i2 R-21.";
    }
  }

  grouping rpf-near-end-line-config {
    description
      "RPF near-end line level configuration.";

    leaf power-extraction {
      type enumeration {
        enum "allowed" {
          description
            "The PE may extract power from this line.";
        }
        enum "not-allowed" {
          description
            "The PE should not extract more than 35 mA at U-O 
             interface (excluding start-up transients) unless the 
             given line is solely reverse powering the DPU or 
             attempting to start-up the DPU.";
        }
      }
      default "allowed";
      description
        "Defines whether or not power extraction from the line is 
         allowed.";
      reference
        "ITU-T G.997.2 clause A.7.1.1.6 (PE-PWR)";
    }

    leaf power-extraction-pse-on-battery {
      type boolean;
      default "false";
      description
        "Defines whether for the line, the PE is allowed to 
         extract power from the line when the PSE reverse power 
         feeding is operating on battery power (PSE-RPF, see 
         clause A.7.4.2.2) and sufficient power is available from 
         one or more remaining reverse power feeding lines for 
         normal operation of the DPU. If 'true', power extraction 
         is allowed. If 'false', only minimal power extraction,
         compliant to the Maintain Power Signature (see Section
         7.5.2.2 of [ETSI TS 101 548]), is allowed.";
      reference
        "ITU-T G.997.2 clause A.7.1.1.1 (PE-PEB)";
    }

    leaf pse-shutdown-service {
      type enumeration {
        enum "force-l3" {
          description
            "Force the line to the L3 link state (no service).";
          reference
            "ITU-T G.997.2 clause A.7.1.1.2 (FL3)";
        }
        enum "enable-l0" {
          description
            "Force the line to an enabled low power link state 
             (limited service).";
          reference
            "ITU-T G.997.2 clause A.7.1.1.2 (NL0)";
        }
        enum "emergency-services-only" {
          description
            "Force the line to support emergency services only 
             (all link states allowed).";
          reference
            "ITU-T G.997.2 clause A.7.1.1.2 (ESO)";
        }
        enum "no-limitations" {
          description
            "No service limitations forced on the line (all link 
             states allowed).";
          reference
            "ITU-T G.997.2 clause A.7.1.1.2 (SRV)";
        }
      }
      default "force-l3";
      description
        "Defines for the line, the FTU/L2+ action when the PSE is 
         in shutdown (PSE-RPF, see clause A.7.4.2.2). Values NL0, 
         ESO, and SRV are conditional to there being sufficient 
         power from one or more remaining reverse power feeding 
         lines available for normal operation of the DPU. If this 
         condition is not met, value FL3 is applied instead.";
      reference
        "ITU-T G.997.2 clause A.7.1.1.2 (FTU-SRV)";
    }

    leaf forced-reconfiguration-state {
      type enumeration {
        enum "none" {
          description
            "No Forced ReConfiguration State. The DPU-FRCS 
             configuration object has no effect on the line's 
             ReConfiguration State.";
        }
        enum "normal" {
          description
            "The line is forced to enter and maintain Normal 
             mode.";
        }
        enum "bypass" {
          description
            "The line is forced to enter and maintain Bypass mode.
             This command is ignored for a given line if this line
             is solely reverse powering the DPU or attempting to 
             start-up the DPU.";
        }
      }
      default "none";
      description
        "Defines for the line, the Forced ReConfiguration State: 
         either None, Normal, or Bypass.";
      reference
        "ITU-T G.997.2 clause A.7.1.1.3 (DPU-FRCS)";
    }

    leaf conditional-forced-reconfiguration-state {
      type enumeration {
        enum "none" {
          description
            "No Conditional Forced ReConfiguration State. The line
             maintains its current ReConfiguration State (see 
             clause A.7.4.1.3).";
        }
        enum "bypass" {
          description
            "The line's ReConfiguration State is forced to Bypass 
             mode.";
        }
      }
      default "none";
      description
        "Defines for the line, the Conditional Forced 
         ReConfiguration State, to be applied upon either 
         enforcing no service on the line (i.e., FTU-SRV value FL3
         is applied, see clause A.7.1.1.2) for a time period T 
         (DPU-CFRCS-T, see clause A.7.1.1.5) or upon DPU 
         shutdown.";
      reference
        "ITU-T G.997.2 clause A.7.1.1.4 (DPU-CFRCS)";
    }

    leaf conditional-forced-reconfiguration-state-time {
      type uint8;
      units "1 second";
      default "30";
      description
        "Defines the time period T to be used with configuration 
         object DPU-CFRCS (see clause A.7.1.1.4).";
      reference
        "ITU-T G.997.2 clause A.7.1.1.5 (DPU-CFRCST)";
    }

    container thresholds {
      description
        "Threshold configuration.";

      leaf dpu-15min-extracted-energy-threshold {
        type uint32;
        units "mWh";
        description
          "Threshold for the count of the DPU extracted energy per
           line at U-O interface or at PSU input in the current
           15 minute interval. A special value (0) indicates the 
           threshold is disabled.";
        reference
          "ITU-T G.997.2 clause A.7.3.4 (CURR/PREV_NE_15/24_EE)";
      }

      leaf dpu-24hr-extracted-energy-threshold {
        if-feature "performance-24hr";
        type uint32;
        units "mWh";
        description
          "Threshold for the count of the DPU extracted energy per
           line at U-O interface or at PSU input in the current
           24 hour interval. A special value (0) indicates the 
           threshold is disabled.";
        reference
          "ITU-T G.997.2 clause A.7.3.5 (CURR/PREV_NE_15/24_IE)";
      }
    }
  }

  grouping rpf-far-end-line-config {
    description
      "RPF far-end line level configuration.";

    container thresholds {
      description
        "Threshold configuration.";

      leaf pse-15min-injected-energy-threshold {
        type uint32;
        units "mWh";
        description
          "Threshold for the count of the PSE injected energy per
           line in the current 15 min interval. A special value 
           (0) indicates the threshold is disabled.";
        reference
          "ITU-T G.997.2 clause A.7.3.5 (CURR/PREV_FE_15/24_IE)";
      }

      leaf pse-24hr-injected-energy-threshold {
        if-feature "performance-24hr";
        type uint32;
        units "mWh";
        description
          "Threshold for the count of the PSE injected energy per
           line in the current 24 hour interval. A special value 
           (0) indicates the threshold is disabled.";
        reference
          "ITU-T G.997.2 clause A.7.3.5 (CURR/PREV_FE_15/24_IE)";
      }
    }
  }

  grouping rpf-threshold-crossing-alerts {
    description
      "Threshold crossing alert notifications.";

    notification rpf-15min-threshold-crossing-alert {
      description
        "A threshold has been crossed during the current 15 minute
         interval.";

      leaf tca-identity {
        type identityref {
          base rpf-15min-threshold-crossing-alert;
        }
        mandatory true;
        description
          "A unique identity associated with each threshold.";
      }
    }

    notification rpf-24hr-threshold-crossing-alert {
      if-feature "performance-24hr";
      description
        "A threshold has been crossed during the current 24 hour
         interval.";

      leaf tca-identity {
        type identityref {
          base rpf-24hr-threshold-crossing-alert;
        }
        mandatory true;
        description
          "A unique identity associated with each threshold.";
      }
    }
  }
}
