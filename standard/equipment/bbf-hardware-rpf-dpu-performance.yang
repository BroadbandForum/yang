submodule bbf-hardware-rpf-dpu-performance {
  yang-version 1.1;
  belongs-to bbf-hardware-rpf-dpu {
    prefix bbf-hw-rpf-dpu;
  }

  import ietf-yang-types {
    prefix yang;
  }

  import bbf-yang-types {
    prefix bbf-yang;
  }

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for 
     reporting the performance of Reverse Power Feeding (RPF)
     for a Distribution Point Unit (DPU).

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }

  feature performance-24hr {
    description
      "Indicates that collection of 24 hour performance intervals
       is supported.";
  }

  typedef performance-15min-interval {
    type uint8 {
      range "0..96";
    }
    description
      "Defines the range of 15 minute intervals.";
  }

  typedef performance-15min-history-interval {
    type performance-15min-interval {
      range "1..96";
    }
    description
      "Defines the range of 15 minutes intervals and defines
       the position of the interval relative to the current interval
       where 1 is the most recent completed interval.";
  }

  typedef performance-24hr-interval {
    type uint8 {
      range "0..7";
    }
    description
      "Defines the range of 24 hour intervals.";
  }

  typedef performance-24hr-history-interval {
    type performance-24hr-interval {
      range "1..7";
    }
    description
      "Defines the range of 24 hour intervals and defines
       the position of the interval relative to the current interval
       where 1 is the most recent completed interval.";
  }

  grouping performance-history-interval-parameters {
    description
      "Defines common parameters required when defining history
       interval performance counters.";

    leaf invalid-data-flag {
      type boolean;
      description
        "Reports the validity of the corresponding PM data.";
    }

    leaf time-stamp {
      type yang:date-and-time;
      description
        "Reports the start date/time for this interval.";
    }
  }

  grouping performance-history-measured-time {
    description
      "Reports the measured time for a given interval";

    leaf measured-time {
      type uint32;
      description
        "Reports the amount of time, measured in seconds,
         that statistics for this interval have been counted.";
    }
  }

  grouping performance-history-15min-interval-parameters {
    description
      "Defines common parameters required when defining 15 minute
       interval history performance counters.";

    uses performance-history-measured-time;
    uses performance-history-interval-parameters;
  }

  grouping performance-history-24hr-interval-parameters {
    description
      "Defines common parameters required when defining 24 hour
       interval history performance counters.";

    uses performance-history-measured-time;
    uses performance-history-interval-parameters;
  }

  grouping performance-15min-history-parameters {
    description
      "Defines common parameters required when defining 15 minute
       history performance counters.";

    leaf number-of-intervals {
      type performance-15min-interval;
      description
        "The total number of 15-minute PM intervals for which data 
         was collected. ";
    }

    leaf non-valid-intervals {
      type performance-15min-interval;
      description
        "The number of 15-minute PM intervals for which the data
         is considered to be invalid or incomplete.";
    }
  }

  grouping performance-24hr-history-parameters {
    description
      "Defines common parameters required when defining 24 hour
       history performance counters.";

    leaf number-of-intervals {
      type performance-24hr-interval;
      description
        "The total number of 24-hour PM intervals for which data 
         was collected. ";
    }

    leaf non-valid-intervals {
      type performance-24hr-interval;
      description
        "The number of 24-hour PM intervals for which the data
         is considered to be invalid or incomplete.";
    }
  }

  grouping near-end-performance-counters {
    description
      "Performance counters associated with the near-end.";

    leaf dpu-extracted-energy {
      type bbf-yang:performance-counter32;
      units "mWh";
      description
        "Reports a count of the DPU extracted energy per line at U-O 
         interface or at PSU input in current/previous interval, 
         expressed in units of mWh. This PM object is optional. 
         The accuracy is defined in [ETSI TS 101 548].";
      reference
        "ITU-T G.997.2 clause A.7.3.4 (CURR/PREV_NE_15/24_EE)";
    }
  }

  grouping far-end-performance-counters {
    description
      "Performance counters associated with the far-end.";

    leaf pse-injected-energy {
      type bbf-yang:performance-counter32;
      units "mWh";
      description
        "Reports a count of the PSE Injected Energy per line in 
         current/previous interval, expressed in units of mWh. This PM
         object is optional. It is constructed by the DPU by reading 
         the RPF OAM parameter PSE-IE (see clause A.6.2.7). It can 
         only be supported in case the PSE is integrated in the NT 
         (see clause A.7.6.2.1, PSE-NTE equals 1). The accuracy is 
         defined in [ETSI TS 101 548].";
      reference
        "ITU-T G.997.2 clause A.7.3.5 (CURR/PREV_NE_15/24_IE)";
    }
  }

  grouping rpf-line-performance {
    description
      "RPF line level performance.";

    container intervals-15min {
      description
        "15 minute interval performance history";

      container current {
        description
          "Contains the counts that are currently accumulating.";

        container near-end {
          description
            "Near-end performance counters.";

          uses performance-history-measured-time;
          uses near-end-performance-counters;
        }

        container far-end {
          description
            "Far-end performance counters.";

          uses performance-history-measured-time;
          uses far-end-performance-counters;
        }
      }

      uses performance-15min-history-parameters;

      list history {
        key "interval-number";
        max-elements 96;
        description
          "A history of 15 minute intervals.";

        leaf interval-number {
          type performance-15min-history-interval;
          description
            "The number of the interval relative to the current
             interval.";
        }

        container near-end {
          description
            "Near-end performance counters.";

          uses performance-history-15min-interval-parameters;
          uses near-end-performance-counters;
        }

        container far-end {
          description
            "Far-end performance counters.";

          uses performance-history-15min-interval-parameters;
          uses far-end-performance-counters;
        }
      }
    }


    container intervals-24hr {
      if-feature "performance-24hr";
      description
        "24 hour interval performance history";

      container current {
        description
          "Contains the counts that are currently accumulating.";

        container near-end {
          description
            "Near-end performance counters.";

          uses performance-history-measured-time;
          uses near-end-performance-counters;
        }

        container far-end {
          description
            "Far-end performance counters.";

          uses performance-history-measured-time;
          uses far-end-performance-counters;
        }
      }

      uses performance-24hr-history-parameters;

      list history {
        key "interval-number";
        max-elements 7;
        description
          "A history of 24 hour intervals.";

        leaf interval-number {
          type performance-24hr-history-interval;
          description
            "The number of the interval relative to the current
             interval.";
        }

        container near-end {
          description
            "Near-end performance counters.";

          uses performance-history-24hr-interval-parameters;
          uses near-end-performance-counters;
        }

        container far-end {
          description
            "Far-end performance counters.";

          uses performance-history-24hr-interval-parameters;
          uses far-end-performance-counters;
        }
      }
    }
  }
}
