module bbf-qos-policies {
  yang-version 1.1;
  namespace "urn:bbf:yang:bbf-qos-policies";
  prefix bbf-qos-pol;

  import ietf-interfaces {
    prefix if;
  }
  import iana-if-type {
    prefix ianaift;
  }
  import bbf-if-type {
    prefix bbfift;
  }
  import bbf-yang-types {
    prefix bbf-yang;
  }
  import bbf-qos-classifiers {
    prefix bbf-qos-cls;
  }

  organization
    "Broadband Forum <https://www.broadband-forum.org>
     Provider Cloud Work Area";
  contact
    "Comments or questions about this Broadband Forum YANG module
     should be directed to <mailto:info@broadband-forum.org>.

     Editor:      Shiya Ashraf, Nokia

     Editor:      Kevin Noll, CableLabs

     PS Leader:   Sven Ooghe, Nokia

     PS Leader:   Joey Boyd, Adtran

     WA Director: Bruno Cornaglia, Vodafone

     WA Director: Mengmeng Li, China Mobile

     WA Director: Haomian Zheng, Huawei";
  description
    "This module contains a collection of YANG definitions for
     supporting the Broadband Forum requirements on the management of
     Quality of Service (QoS) as applicable to access network
     equipment. As such, this module is specific to access network
     equipment (e.g., BBF-specified Access Nodes and FTTdp DPUs).

     Specifically, this module contains a collection of policies that
     can be used to control the flow of frames.

     Copyright (c) 2017-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a9; see
     the TR itself for full legal notices.";

  revision 2025-07-02 {
    description
      "Amendment 9.
       * Approval Date:    2025-07-02.
       * Publication Date: 2025-07-02.";
    reference
      "TR-383a9: Common YANG Modules for Access Networks
                 <https://www.broadband-forum.org/technical/download/
                          TR-383_Amendment-9.pdf>";
  }
  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }
  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2018-12-03 {
    description
      "Amendment 2.
       * Approval Date:    2018-12-03.
       * Publication Date: 2018-12-03.";
    reference
      "TR-383a2: Common YANG Modules
               <https://www.broadband-forum.org/technical/download/
                        TR-383_Amendment-2.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  feature interface-policy-management {
    description
      "Indicates support for managing QoS policies per interface.";
  }

  typedef qos-policy-profile-ref {
    type leafref {
      path "/bbf-qos-pol:qos-policy-profiles/bbf-qos-pol:policy-"
         + "profile/bbf-qos-pol:name";
    }
    description
      "The name of the referenced QoS policy profile.";
  }

  grouping qos-policy-profiles {
    description
      "Provides references to QoS policy profiles.";
    leaf ingress-qos-policy-profile {
      type qos-policy-profile-ref;
      description
        "A reference to a QoS policy profile. The profile is to be
         applied to incoming frames.";
    }
    leaf egress-qos-policy-profile {
      type qos-policy-profile-ref;
      description
        "A reference to a QoS policy profile. The profile is to be
         applied to outgoing frames.";
    }
  }

  grouping policy-entry-ref {
    description
      "A reference to a policy entry.";
    leaf name {
      type leafref {
        path "/bbf-qos-pol:policies/bbf-qos-pol:policy/bbf-qos-pol:"
           + "name";
      }
      description
        "The name of the referenced policy entry.";
    }
  }

  container policies {
    description
      "Configuration associated with policies.";
    list policy {
      key "name";
      description
        "A QoS policy.";
      leaf name {
        type bbf-yang:string-ascii64;
        description
          "Name of the policy.";
      }
      leaf description {
        type bbf-yang:string-ascii64-or-empty;
        description
          "Description of the policy.";
      }
      list classifiers {
        key "name";
        ordered-by user;
        description
          "Provides a list of classifiers which are evaluated in
           order as specified by the user. When a classifier is
           matched, no other classifiers are evaluated.";
        uses bbf-qos-cls:classifier-entry-ref;
      }
    }
  }
  container qos-policy-profiles {
    description
      "This container provides a framework for QoS policy profile
       configuration.";
    list policy-profile {
      key "name";
      description
        "A QoS policy profile.";
      leaf name {
        type bbf-yang:string-ascii64;
        description
          "Name of the QoS policy profile.";
      }
      list policy-list {
        key "name";
        ordered-by user;
        description
          "Provides ordered lists of policies for the ingress and for
           the egress direction.

           The definition is that all policies are executed in the
           order of the list. The output of one policy is used as
           input for the next policy.";
        uses policy-entry-ref;
      }
    }
  }

  augment "/if:interfaces/if:interface" {
    when
      "derived-from-or-self(if:type, 'ianaift:ethernetCsmacd') or "
    + "derived-from-or-self(if:type, 'ianaift:ieee8023adLag') or "
    + "derived-from-or-self(if:type, 'ianaift:ptm') or "
    + "derived-from-or-self(if:type, 'bbfift:vlan-sub-interface') or "
    + "derived-from-or-self(if:type, 'bbfift:l2-termination') or "
    + "derived-from(if:type, 'bbfift:ethernet-like')" {
      description
        "Applies only to those types of interfaces that can have QoS
         policy profiles assigned.";
    }
    description
      "Add data nodes to manage the assignment of QoS policy profile
       to an interface.

       If several interfaces linked by a parent-child relationship in
       the interface stack are configured with a QoS policy profile of
       the same type (e.g., an 'ingress-qos-policy-profile'), then all
       referenced QoS policies must be applied in the order specified
       below.

       In the case of ingress, the QoS policies referenced by the QoS
       policy profile configured on the lower-level interface(s)
       (e.g., 'ethernetCsmacd') must first be applied, followed by the
       QoS policies referenced by the QoS policy profile configured on
       the on the upper-level interface(s) (e.g.,
       'vlan-sub-interface').

       In the case of egress, the QoS policies referenced by the QoS
       policy profile configured on the upper-level interface(s)
       (e.g., 'vlan-sub-interface') must first be applied followed by
       the QoS policies referenced by the QoS policy profile
       configured on the lower-level interface(s) (e.g.,
       'ethernetCsmacd').";
    uses qos-policy-profiles;
  }

  augment "/if:interfaces/if:interface" {
    when
      "derived-from-or-self(if:type, 'ianaift:ethernetCsmacd') or "
    + "derived-from-or-self(if:type, 'ianaift:ieee8023adLag') or "
    + "derived-from-or-self(if:type, 'ianaift:ptm') or "
    + "derived-from-or-self(if:type, 'bbfift:vlan-sub-interface') or "
    + "derived-from-or-self(if:type, 'bbfift:l2-termination') or "
    + "derived-from(if:type, 'bbfift:ethernet-like')" {
      description
        "Interfaces that may support QoS policy management.";
    }
    description
      "Augment interface management with QoS policy
       management.";
    container qos-policies {
      if-feature "interface-policy-management";
      presence
        "Indicates that the management of QoS policies is enabled on
         this interface.";
      description
        "Management associated with QoS policies.";
    }
  }
}
