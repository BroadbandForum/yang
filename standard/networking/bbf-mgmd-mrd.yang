module bbf-mgmd-mrd {
  yang-version 1.1;
  namespace "urn:bbf:yang:bbf-mgmd-mrd";
  prefix bbf-mgmd-mrd;

  import ietf-yang-types {
    prefix yang;
  }
  import ietf-inet-types {
    prefix inet;
  }
  import bbf-mgmd {
    prefix bbf-mgmd;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on layer 2 multicast
     management as applicable to access network equipment. As such,
     this module is specific to access network equipment (e.g.,
     BBF-specified Access Nodes and FTTdp DPUs).

     Specifically,this module contains a collection of YANG
     definitions for supporting the Multicast Group Membership
     Discovery (MGMD) Protocols. In particular, it describes data
     nodes used for managing the Internet Group Management Protocol
     (IGMP) and the Multicast Listener Discovery (MLD) protocol in
     systems that act as a multicast proxy, snooper, or a snooper with
     proxy reporting.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a6; see
     the TR itself for full legal notices.";

  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }
  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }

  augment "/bbf-mgmd:multicast/bbf-mgmd:mgmd/bbf-mgmd:multicast-vpn" {
    description
      "Augment MGMD Multicast VPN to include Multicast Routing
       Discovery protocol as per RFC 4286.";
    container mgmd-mrd {
      description
        "Configuration associated with the Multicast Routing Discovery
         (MRD) protocol.";
      leaf neighbor-dead-interval {
        type uint32;
        description
          "Neighbor dead interval is the maximum time (in seconds)
           allowed to elapse (after receipt of the last valid
           Advertisement) before a neighboring router is declared
           unreachable. If not specified, the default is the Neighbor
           Dead Interval times the sum of Advertisement Interval Field
           received (in the MRD Advertisement Packet) plus the derived
           Advertisement Jitter from the received Advertisement
           Interval field (as per RFC 4286, the advertisement jitter
           is 0.025*Advertisement Interval).";
      }
      choice ip-layer {
        when "../bbf-mgmd:mode = 'bbf-mgmd:snoop-transparent'";
        description
          "Provides the mechanism to add IP addressing information
           to the multicast network interface for MRD Solicit
           Packet address.";
        case ip-address {
          leaf ipv4-address {
            when "../../bbf-mgmd:ip-version = 'ipv4'";
            type inet:ipv4-address;
            description
              "The IPv4 address to be used as source IP address. If
               not specified, it defaults to the management address of
               the device.";
          }
        }
      }
    }
  }

  augment "/bbf-mgmd:multicast-state/bbf-mgmd:mgmd/bbf-mgmd:"
        + "multicast-vpn" {
    description
      "Augment MGMD Multicast VPN state to include statistics on
       number of incoming/outgoing Multicast Routing Discovery
       messages.";
    container mgmd-mrd-statistics {
      description
        "Statistics associated with the Multicast Routing Discovery
         (MRD) protocol.";
      leaf out-solicit {
        type yang:counter32;
        units "messages";
        description
          "Number of outgoing MRD Solicit messages.";
      }
      leaf in-termination {
        type yang:counter32;
        units "messages";
        description
          "Number of incoming MRD Termination messages.";
      }
      leaf in-advertisement {
        type yang:counter32;
        units "messages";
        description
          "Number of incoming MRD Advertisement messages.";
      }
    }
  }
}
