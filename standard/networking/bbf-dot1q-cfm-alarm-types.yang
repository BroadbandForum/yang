module bbf-dot1q-cfm-alarm-types {
  yang-version 1.1;
  namespace "urn:bbf:yang:bbf-dot1q-cfm-alarm-types";
  prefix bbf-cfm-alt;

  import bbf-alarm-types {
    prefix bbf-alt;
  }

  organization
    "Broadband Forum <https://www.broadband-forum.org>
     Provider Cloud Work Area";
  contact
    "Comments or questions about this Broadband Forum YANG module
     should be directed to <mailto:info@broadband-forum.org>.

     Editor:      Shiya Ashraf, Nokia

     Editor:      Kevin Noll, CableLabs

     PS Leader:   Sven Ooghe, Nokia

     PS Leader:   Joey Boyd, Adtran

     WA Director: Bruno Cornaglia, Vodafone

     WA Director: Mengmeng Li, China Mobile

     WA Director: Haomian Zheng, Huawei";
  description
    "This module contains a collection of YANG definitions for
     supporting the Broadband Forum requirements on Connectivity Fault
     Management (CFM) Operations, Administration, and Maintenance
     (OAM) as applicable to access network equipment. As such, this
     module is specific to access network equipment (e.g.,
     BBF-specified Access Nodes and FTTdp DPUs).

     Specifically, this module contains a set of alarm definitions.

     Copyright (c) 2017-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a9; see
     the TR itself for full legal notices.";

  revision 2025-07-02 {
    description
      "Amendment 9.
       * Approval Date:    2025-07-02.
       * Publication Date: 2025-07-02.";
    reference
      "TR-383a9: Common YANG Modules for Access Networks
                 <https://www.broadband-forum.org/technical/download/
                          TR-383_Amendment-9.pdf>";
  }
  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }

  identity cfm-alarm-type-id {
    base bbf-alt:bbf-alarm-type-id;
    description
      "Base identity for Connectivity Fault Management (CFM) alarms.

       This identity is abstract and should not generally be used for
       alarms. If used to define an alarm that was not known at
       design time, it must be qualified with an alarm type qualifier
       string. This practice, however, should be generally avoided to
       ensure all possible alarms are known at design time.";
  }

  identity cross-connect-ccm {
    base bbf-cfm-alt:cfm-alarm-type-id;
    description
      "Indicates that the Maintenance Association Endpoint (MEP) has
       received at least one Continuity Check Message (CCM) from
       either another Maintenance Association Identifier (MAID) or a
       lower Maintenance Domain (MD) level whose CCM Interval has not
       yet timed out.";
    reference
      "IEEE 802.1Q-2018 Section 20.23.3 and Table 20-1";
  }

  identity error-ccm {
    base bbf-cfm-alt:cfm-alarm-type-id;
    description
      "Indicates that the MEP has received at least one invalid CCM
       whose CCM Interval has not yet timed out.";
    reference
      "IEEE 802.1Q-2018 Section 20.21.3 and Table 20-1";
  }

  identity remote-ccm {
    base bbf-cfm-alt:cfm-alarm-type-id;
    description
      "Indicates that the MEP is not receiving valid CCMs from at
       least one of the remote MEPs.";
    reference
      "IEEE 802.1Q-2018 Section 20.35.5 and Table 20-1";
  }

  identity mac-status {
    base bbf-cfm-alt:cfm-alarm-type-id;
    description
      "Indicates that either some remote MEP is reporting its
       Interface Status TLV as not isUp, or all remote MEPs are
       reporting a Port Status TLV that contains some value other
       than psUp.";
    reference
      "IEEE 802.1Q-2018 Section 20.35.6 and Table 20-1";
  }

  identity rdi-ccm {
    base bbf-cfm-alt:cfm-alarm-type-id;
    description
      "Indicates that at least one remote MEP reported the Remote
       Defect Indication (RDI) bit in its last CCM.";
    reference
      "IEEE 802.1Q-2018 Section 20.35.7 and Table 20-1";
  }
}
