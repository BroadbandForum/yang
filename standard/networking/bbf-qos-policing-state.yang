module bbf-qos-policing-state {
  yang-version 1.1;
  namespace "urn:bbf:yang:bbf-qos-policing-state";
  prefix bbf-qos-plc-s;

  import bbf-qos-policies-state {
    prefix bbf-qos-pol-s;
  }
  import bbf-qos-policing {
    prefix bbf-qos-plc;
  }
  import bbf-yang-types {
    prefix bbf-yang;
  }
  import ietf-interfaces {
    prefix if;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Broadband Forum requirements on the management of
     Quality of Service (QoS) as applicable to access network
     equipment. As such, this module is specific to access network
     equipment (e.g., BBF-specified Access Nodes and FTTdp DPUs).

     Specifically, this module augments interfaces to add monitoring
     the policing of flows. This module is to be used, along with
     'bbf-qos-policing' when the server does not support Network
     Management Datastore Architecture (NMDA) as defined in RFC 8342.

     Copyright (c) 2017-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a4; see
     the TR itself for full legal notices.";

  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }

  grouping policing-state-data {
    description
      "Policing state data.";
    list policer {
      key "name";
      description
        "A policer's state data.";
      leaf name {
        type bbf-yang:string-ascii64;
        description
          "The name of a policer profile that defines a policer within
           the current scope.";
      }
      uses bbf-qos-plc:policing-statistics;
    }
  }

  augment "/if:interfaces-state/if:interface"
        + "/bbf-qos-pol-s:qos-policies"
        + "/bbf-qos-pol-s:ingress"
        + "/bbf-qos-pol-s:policy"
        + "/bbf-qos-pol-s:classifier" {
    description
      "Augment policing state data onto classifiers associated with
       the ingress QoS policies associated with an interface.";
    container policing {
      presence
        "The presence of this container indicates the classifier
         contains an entry whose action is to police or otherwise
         mark the color of frames.";
      description
        "Policing state data.";
      uses bbf-qos-plc:policing-statistics;
    }
  }

  augment "/if:interfaces-state/if:interface"
        + "/bbf-qos-pol-s:qos-policies"
        + "/bbf-qos-pol-s:egress"
        + "/bbf-qos-pol-s:policy"
        + "/bbf-qos-pol-s:classifier" {
    description
      "Augment policing state data onto classifiers associated with
       the egress QoS policies associated with an interface.";
    container policing {
      presence
        "The presence of this container indicates the classifier
         contains an entry whose action is to police or otherwise
         mark the color of frames.";
      description
        "Policing state data.";
      uses bbf-qos-plc:policing-statistics;
    }
  }

  augment "/if:interfaces-state/if:interface/"
        + "bbf-qos-pol-s:qos-policies/bbf-qos-pol-s:ingress" {
    description
      "Augment the ingress QoS policy state data for interfaces to
       report policing state data.";
    container policing {
      presence
        "The presence of this container indicates ingress policing
         state data is available on this interface.";
      description
        "Policing state data.";
      uses policing-state-data;
    }
  }

  augment "/if:interfaces-state/if:interface/"
        + "bbf-qos-pol-s:qos-policies/bbf-qos-pol-s:egress" {
    description
      "Augment the egress QoS policy state data for interfaces to
       report policing state data.";
    container policing {
      presence
        "The presence of this container indicates egress policing
         state data is available on this interface.";
      description
        "Policing state data.";
      uses policing-state-data;
    }
  }
}
