module bbf-icmpv6-forwarding {
  yang-version 1.1;
  namespace "urn:bbf:yang:bbf-icmpv6-forwarding";
  prefix bbf-icmpv6-fwd;

  import ietf-yang-types {
    prefix yang;
  }
  import bbf-l2-forwarding {
    prefix bbf-l2-fwd;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on subscriber
     management via the Internet Control Message Protocol version 6
     (ICMPv6) protocol as applicable to access network equipment. As
     such, this module is specific to access network equipment (e.g.,
     BBF-specified Access Nodes and FTTdp DPUs).

     Specifically, this module augments bbf-l2-forwarding with data
     nodes controlling the forwarding of ICMPv6 messages.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }

  augment "/bbf-l2-fwd:forwarding/bbf-l2-fwd:forwarders/bbf-l2-fwd:"
        + "forwarder" {
    description
      "Additions for the ICMPv6 Relay at the forwarder level.";
    container icmpv6 {
      presence "Indicates that the ICMPv6 Relay functionality is to be
                managed in the context of this forwarder.";
      description
        "Configuration for the forwarding of ICMPv6 messages through a
         forwarder.";
      leaf downstream-multicast-flooding {
        type union {
          type boolean;
          type enumeration {
            enum single-user-with-fallback-to-layer2 {
              description
                "Downstream multicast ICMPv6 messages are first
                 processed as defined for the value 'false', i.e.,
                 they are forwarded to only one port of the forwarder
                 which is identified by the ICMPv6 message content.
                 If, however, no port is identified in this way, then
                 the message will be processed based on the (flooding)
                 forwarding rules of the forwarder.";
            }
          }
        }
        default "false";
        description
          "If 'true', the ICMPv6 Relay will flood downstream
           'multicast ICMPv6 messages' to all output ports of the
           forwarder (overruling the layer 2 flooding configuration).

           If 'false', the ICMPv6 Relay will forward downstream
           'multicast ICMPv6 messages' to only one port of the
           forwarder, i.e., the one for which the message is intended.
           Identifying the port for which the message is intended is
           based on frame content. If no such port can be identified
           the message is discarded.

           Otherwise, the ICMPv6 Relay will forward downstream
           'multicast ICMPv6 messages' as defined in the selected
            enumeration.";
        reference
          "TR-177 R-14;
           TR-177 R-17";
      }
    }
  }

  augment "/bbf-l2-fwd:forwarding-state/bbf-l2-fwd:forwarders/"
        + "bbf-l2-fwd:forwarder" {
    description
      "Additions for the ICMPv6 Relay at the forwarder level.";
    container icmpv6 {
      description
        "State data related to the forwarding of ICMPv6 messages
         through a forwarder.";
      container router-solicitation {
        description
          "ICMPv6 Router Solicitation statistics.";
        leaf discarded-messages {
          type yang:counter32;
          description
            "Number of messages discarded.";
          reference
            "TR-177 R-17";
        }
      }
    }
  }
}
