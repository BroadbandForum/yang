submodule bbf-mgmd-configuration-multicast-snoop {
  yang-version 1.1;
  belongs-to bbf-mgmd {
    prefix bbf-mgmd;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This submodule contains a collection of YANG definitions for
     supporting the Multicast Group Membership Discovery (MGMD)
     Protocols. In particular, it describes configuration data nodes
     used for managing the Internet Group Management Protocol (IGMP)
     and the Multicast Listener Discovery (MLD) protocol in case the
     system acts as a snooper.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a6; see
     the TR itself for full legal notices.";

  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }
  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2019-10-21 {
    description
      "Amendment 2 Corrigendum 1.
       * Approval Date:    2019-10-21.
       * Publication Date: 2019-10-21.";
    reference
      "TR-383a2c1: Common YANG Modules
                 <https://www.broadband-forum.org/technical/download/
                          TR-383_Amendment-2.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }

  feature mgmd-snoop-last-leave {
    description
      "MGMD snoop last leave functionality is supported.";
  }

  grouping multicast-snoop {
    description
      "Data nodes used for configuring the Internet Group Management
       Protocol (IGMP) and the Multicast Listener Discovery (MLD)
       protocol on a layer 2 system that connects multicast hosts
       and multicast routers and for which the system acts as a
       MGMD snooper.";
    leaf immediate-leave {
      type enumeration {
        enum enabled {
          description
            "Immediate leave enabled means the system performs host
             tracking. Then the reception of a leave results in
             immediately removing this host from the subscription
             list.";
        }
        enum disabled {
          description
            "Immediate leave disabled means the system sends MGMD
             Group-Specific Query messages on the interface to find
             out if other hosts connected to the same interface would
             still be interested in receiving the multicast channel.";
        }
      }
      default "disabled";
      description
        "Immediate leave controls the function by which an interface
         that receives a leave for a certain group might immediately
         delete the corresponding group record.

         Configuring immediate leave reduces the amount of time it
         takes for the switch to stop sending multicast traffic to an
         interface when the last host on that interface leaves the
         group.

         When immediate leave is disabled, the switch no longer tracks
         hosts. Instead, whenever it receives a leave from a host on
         an interface, it waits for a period as specified by the group
         membership interval. If it does not receive any MGMD
         Membership Report on the interface in that time interval, it
         stops forwarding multicast traffic to the interface.";
      reference
        "ITU-T G.988 clause 9.3.27, Immediate Leave;
         RFC 3810 section A.2";
    }
    leaf group-membership-interval {
      type uint32 {
        range "1..31744";
      }
      units "seconds";
      default "260";
      description
        "The group membership interval is the amount of time that has
         to pass before a multicast router decides there are no more
         members of a group or a particular source on an interface.

         This leaf, as a parameter of a snooper, has to be consistent
         with the parameters configured in the multicast router that
         is connected to the snooper. It has to be equal to or larger
         than ((the Robustness Variable) times (the Query Interval))
         plus (one Query Response Interval) as calculated from
         parameters configured in the multicast router.";
      reference
        "RFC 4541 section 2.1.1, item 6;
         RFC 3376 section 8.4";
    }
    leaf last-member-query-interval {
      if-feature "bbf-mgmd:mgmd-snoop-last-leave";
      type uint32 {
        range "2..31744";
      }
      units "0.1 seconds";
      default "10";
      description
        "The last member query interval is the maximum response time
         inserted into MGMD Group-Specific Query messages sent in
         response to leaves, and is also the amount of time between
         MGMD Group-Specific Query messages.

         This feature is optional for a snooper and can be used in a
         slow network. When this feature is enabled, it permits a
         snooper to send a MGMD Group-Specific Query message after the
         group membership has timed out to verify that clients have
         stopped watching a channel. If no response is received to the
         MGMD Group-Specific Query message, it removes the group state
         and discontinuous multicast transmission for that channel";
      reference
        "RFC 3376 section 8.8;
         RFC 5519 section 5,
         mgmdRouterInterfaceLastMemberQueryInterval";
    }
    leaf last-member-query-count {
      if-feature "bbf-mgmd:mgmd-snoop-last-leave";
      type uint32 {
        range "1..255";
      }
      default "2";
      description
        "The number of unanswered MGMD Group-Specific Query messages
         sent out before it is assumed that there are no local members
         interested in the IP multicast stream.

         This feature is optional for a snooper and can be used in a
         slow network. When this feature is enabled, it permits a
         snooper to send a MGMD Group-Specific Query message after the
         group membership has timed out to verify that clients have
         stopped watching a channel. If no response is received to the
         MGMD Group-Specific Query message, it removes the group state
         and discontinuous multicast transmission for that channel";
      reference
        "RFC 3376 section 8.9";
    }
  }
}
