module bbf-dot1q-cfm {
  yang-version 1.1;
  namespace "urn:bbf:yang:bbf-dot1q-cfm";
  prefix bbf-cfm;

  import ieee802-dot1q-cfm {
    prefix dot1q-cfm;
  }
  import bbf-interface-usage {
    prefix bbf-if-usg;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     WA Director: Joey Boyd, ADTRAN

     WA Director: Sven Ooghe, Nokia";
  description
    "This module is part of a collection of YANG definitions for
     supporting the Broadband Forum requirements on Connectivity Fault
     Management (CFM) Operations, Administration, and Maintenance
     (OAM) as applicable to access network equipment. As such, this
     module is specific to access network equipment (e.g., BBF-
     specified Access Nodes and FTTdp DPUs).

     Specifically, this module augments the IEEE 802.1Qcx CFM YANG
     data model with data nodes to support BBF-specific requirements.

     Copyright (c) 2017-2022, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a5; see
     the TR itself for full legal notices.";

  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }

  feature discard-ingressing-ltm {
    description
      "Indicates support for discarding Link Trace Message (LTM) OAM
       Protocol Data Units (PDU) at an interface.";
    reference
      "TR-101 Issue 2, R-301";
  }

  grouping local-mep {
    description
      "Defines the parameters that uniquely identify a local
       Maintenance Association (MA) End Point (MEP).";
    leaf maintenance-group-id {
      type leafref {
        path "/dot1q-cfm:cfm/dot1q-cfm:maintenance-group"
           + "/dot1q-cfm:maintenance-group-id";
      }
      mandatory true;
      description
        "The Maintenance Group that the MEP is associated with.";
    }
    leaf mep-id {
      type leafref {
        path "/dot1q-cfm:cfm"
           + "/dot1q-cfm:maintenance-group"
           + "[dot1q-cfm:maintenance-group-id = current()"
           + "/../maintenance-group-id]"
           + "/dot1q-cfm:mep/dot1q-cfm:mep-id";
      }
      mandatory true;
      description
        "A Maintenance Association Endpoint Identifier of a local
         MEP.";
      reference
        "12.14.2.1.3d of IEEE Std 802.1Q-2018";
    }
  }

  grouping local-mhf {
    description
      "Defines the parameters that uniquely identify a local
       Maintenance Domain Intermediate Point (MIP) Half Function
       (MHF).";
    choice mip-creation {
      case auto-created {
        leaf md-id {
          type leafref {
            path "/dot1q-cfm:cfm/dot1q-cfm:maintenance-domain"
               + "/dot1q-cfm:md-id";
          }
          mandatory true;
          description
            "The Maintenance Domain that the MHF is associated with.";
        }
        leaf ma-id {
          type leafref {
            path "/dot1q-cfm:cfm"
               + "/dot1q-cfm:maintenance-domain"
               + "[dot1q-cfm:md-id = current()/../md-id]"
               + "/dot1q-cfm:maintenance-association/dot1q-cfm:ma-id";
          }
          mandatory true;
          description
            "The Maintenance Association that the MHF is associated
             with.";
        }
      }
      mandatory true;
      description
        "Identifies where the MIP exists.";
    }
  }

  augment "/dot1q-cfm:cfm/dot1q-cfm:maintenance-domain/"
        + "dot1q-cfm:maintenance-association" {
    description
      "Augment the Maintenance Association data.";
    leaf-list discard-ingressing-ltm {
      if-feature "discard-ingressing-ltm";
      type bbf-if-usg:interface-usage;
      description
        "Indicates a type of interface usage from which ingressing
         LTMs received by a MIP configured in this Maintenance
         Association are to be discarded, because the device
         generating the LTM on that type of interface is considered to
         be non-trusted.

         The interface usage not being added to this list means the
         devices connected to that type of interface are trusted. An
         empty list or a non-existing leaf means all peer devices are
         trusted and LTM messages will not be discarded.";
      reference
        "TR-101 Issue 2, R-301";
    }
  }
}
