module bbf-vlan-sub-interface-profile-dhcpv6 {
  yang-version 1.1;
  namespace "urn:bbf:yang:bbf-vlan-sub-interface-profile-dhcpv6";
  prefix bbf-vsi-prof-dhcpv6;

  import bbf-vlan-sub-interface-profiles {
    prefix bbf-vsi-prof;
  }
  import bbf-ldra {
    prefix bbf-ldra;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on the management of
     sub-interfaces as applicable to access network equipment. As
     such, this module is specific to access network equipment (e.g.,
     BBF-specified Access Nodes and FTTdp DPUs).

     Specifically, this module extends the VLAN sub-interface profile
     with DHCPv6 data nodes.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }

  augment "/bbf-vsi-prof:vsi-profiles"
        + "/bbf-vsi-prof:vsi-profile" {
    description
      "Augments the VLAN sub-interface profile with DHCPv6 data
       nodes.";
    container dhcpv6-ldra {
      presence
        "Enables support of a Lightweight DHCPv6 Relay Agent (LDRA) on
         interfaces referencing this profile.";
      description
        "Lightweight DHCPv6 Relay Agent (LDRA) configuration
         parameters.";
      leaf trusted-port {
        type boolean;
        default "false";
        description
          "Marks a client-facing interface as trusted for the LDRA.
           When an interface is deemed untrusted, i.e., configured
           'false', then the LDRA must discard any message of type
           RELAY-FORW (12) received from the client-facing interface.
           When an interface is trusted i.e;, configured 'true', then
           the RELAY-FORW DHCPv6 message coming from an LDRA, or other
           messages coming from a client such as a Solicit message,
           are forwarded embedded in a new RELAY-FORW message.";
        reference
          "RFC 6221 Section 6.1.2";
      }
      leaf profile-ref {
        type leafref {
          path "/bbf-ldra:dhcpv6-ldra-profiles/bbf-ldra:dhcpv6-"
             + "ldra-profile/bbf-ldra:name";
        }
        mandatory true;
        description
          "Reference to the DHCPv6 configuration profile.";
      }
    }
  }
}
