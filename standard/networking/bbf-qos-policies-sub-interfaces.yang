module bbf-qos-policies-sub-interfaces {
  yang-version 1.1;
  namespace "urn:bbf:yang:bbf-qos-policies-sub-interfaces";
  prefix bbf-qos-pol-subif;

  import ietf-interfaces {
    prefix if;
  }
  import bbf-sub-interfaces {
    prefix bbf-subif;
  }
  import bbf-sub-interface-tagging {
    prefix bbf-subif-tag;
  }
  import bbf-frame-processing-types {
    prefix bbf-fpt;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on the management of
     Quality of Service (QoS) as applicable to access network
     equipment. As such, this module is specific to access network
     equipment (e.g., BBF-specified Access Nodes and FTTdp DPUs).

     Specifically, this module augments sub-interfaces to support
     policies to control the flow of frames.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a6; see
     the TR itself for full legal notices.";

  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }
  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2018-12-03 {
    description
      "Amendment 2.
       * Approval Date:    2018-12-03.
       * Publication Date: 2018-12-03.";
    reference
      "TR-383a2: Common YANG Modules
               <https://www.broadband-forum.org/technical/download/
                        TR-383_Amendment-2.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  augment "/if:interfaces/if:interface/bbf-subif:frame-processing/"
        + "bbf-subif:inline-frame-processing/bbf-subif:inline-"
        + "frame-processing/bbf-subif:ingress-rule/bbf-subif:rule/"
        + "bbf-subif:ingress-rewrite/bbf-subif-tag:push-tag/bbf-"
        + "subif-tag:dot1q-tag/bbf-subif-tag:pbit" {
    description
      "Allows for the p-bits of VLAN tag of a frame to be derived from
       a QoS policy profile.";
    case generate-pbit-via-profile-or-0 {
      description
        "The p-bits are generated via a QoS policy profile attached to
         the VLAN sub-interface.

         If no p-bits are generated via the profile, or if no profile
         is assigned to the interface, then p-bits=000 is pushed in
         the VLAN tag of the frame.";
      leaf pbit-marking-index {
        type bbf-fpt:qos-pbit-marking-index;
        description
          "Applying a QoS policy while processing a frame can generate
           more than one metadata value for the p-bits (for possible
           usage in multiple VLAN tags). In this case each of them is
           identified by an index.

           This leaf provides the index in the metadata list of p-bits
           values from which the value shall be taken to put in
           the frame's VLAN tag.";
      }
    }
  }

  augment "/if:interfaces/if:interface/bbf-subif:frame-processing/"
        + "bbf-subif:inline-frame-processing/bbf-subif:inline-"
        + "frame-processing/bbf-subif:ingress-rule/bbf-subif:rule/"
        + "bbf-subif:ingress-rewrite/bbf-subif-tag:push-tag/bbf-"
        + "subif-tag:dot1q-tag/bbf-subif-tag:dei" {
    description
      "Allows for the DEI bit of VLAN tag of a frame to be derived
       from a QoS policy profile.";
    case generate-dei-via-profile-or-0 {
      description
        "The DEI bit is generated via a QoS policy profile attached to
         the VLAN sub-interface.

         If no DEI bit is generated via the profile, or if no profile
         is assigned to the interface, then DEI bit=0 is pushed in the
         VLAN tag of the frame.";
      leaf dei-marking-index {
        type bbf-fpt:qos-dei-marking-index;
        description
          "Applying a QoS policy while processing a frame can generate
           more than one metadata value for the DEI bit (for possible
           usage in multiple VLAN tags). In this case each of them is
           identified by an index.

           This leaf provides the index in the metadata list of DEI
           bit values from which the value shall be taken to put in
           the frame's VLAN tag.";
      }
    }
  }

  augment "/if:interfaces/if:interface/bbf-subif:frame-processing/"
        + "bbf-subif:inline-frame-processing/bbf-subif:inline-"
        + "frame-processing/bbf-subif:egress-rewrite/bbf-subif-tag:"
        + "push-tag/bbf-subif-tag:dot1q-tag/bbf-subif-tag:pbit" {
    description
      "Allows for the p-bits to be derived from a QoS policy
       profile.";
    case generate-pbit-via-profile-or-0 {
      description
        "The p-bits are generated via a QoS policy profile attached to
         the VLAN sub-interface.

         If no p-bits are generated via the profile, or if no profile
         is assigned to the interface, then p-bits=000 is pushed in
         the VLAN tag of the frame.";
      leaf pbit-marking-index {
        type bbf-fpt:qos-pbit-marking-index;
        description
          "Applying a QoS policy while processing a frame can generate
           more than one metadata value for the p-bits (for possible
           usage in multiple VLAN tags). In this case each of them is
           identified by an index.

           This leaf provides the index in the metadata list of p-bits
           values from which the value shall be taken to put in
           the frame's VLAN tag.";
      }
    }
  }

  augment "/if:interfaces/if:interface/bbf-subif:frame-processing/"
        + "bbf-subif:inline-frame-processing/bbf-subif:inline-"
        + "frame-processing/bbf-subif:egress-rewrite/bbf-subif-tag:"
        + "push-tag/bbf-subif-tag:dot1q-tag/bbf-subif-tag:dei" {
    description
      "Allows for the DEI to be derived from a QoS policy profile.";
    case generate-dei-via-profile-or-0 {
      description
        "The DEI bits are generated via a QoS policy profile attached
         to the VLAN sub-interface.

         If no DEI bits are generated via the profile, or if no
         profile is assigned to the interface, then DEI bit = 0 is
         pushed in the VLAN tag of the frame.";
      leaf dei-marking-index {
        type bbf-fpt:qos-dei-marking-index;
        description
          "Applying a QoS policy while processing a frame can generate
           more than one metadata value for the DEI bit (for possible
           usage in multiple VLAN tags). In this case each of them is
           identified by an index.

           This leaf provides the index in the metadata list of DEI
           bit values from which the value shall be taken to put in
           the frame's VLAN tag.";
      }
    }
  }
}
