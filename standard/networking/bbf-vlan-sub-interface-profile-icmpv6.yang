module bbf-vlan-sub-interface-profile-icmpv6 {
  yang-version 1.1;
  namespace "urn:bbf:yang:bbf-vlan-sub-interface-profile-icmpv6";
  prefix bbf-vsi-prof-icmpv6;

  import bbf-vlan-sub-interface-profiles {
    prefix bbf-vsi-prof;
  }
  import bbf-icmpv6 {
    prefix bbf-icmpv6;
  }
  import bbf-icmpv6-profile-common {
    prefix bbf-icmpv6-pc;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on the management of
     sub-interfaces as applicable to access network equipment. As
     such, this module is specific to access network equipment (e.g.,
     BBF-specified Access Nodes and FTTdp DPUs).

     Specifically, this module extends the VLAN sub-interface profile
     with ICMPv6 data nodes.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }

  augment "/bbf-vsi-prof:vsi-profiles"
        + "/bbf-vsi-prof:vsi-profile" {
    description
      "Augments the VLAN sub-interface profile with ICMPv6 data
       nodes.";
    container icmpv6 {
      presence
        "Enables ICMPv6 message processing on interfaces referencing
         this profile.";
      description
        "ICMPv6 message processing configuration parameters.";
      leaf enabled {
        type union {
          type enumeration {
            enum true {
              description
                "The ICMPv6 Relay will process ICMPv6 messages
                 received on the interface as defined in the
                 referenced Technical Report:
                 - Discard messages that are only sent by routers,
                   i.e., Router Advertisement, Redirect, MLD Query
                   messages.
                 - Relay the received Router Solicitation within a new
                   IPv6 datagram and insert a LIO.
                 - Forward other ICMPv6 messages as normal layer 2
                   frames

                 The downstream IPv6 datagram received as a reply will
                 be unpacked and the Router Advertisement message
                 included within will be sent on the interface
                 identified by the LIO.

                 Downstream ICMPv6 messages that can come from a
                 router are forwarded, Downstream ICMPv6 messages that
                 can come only from a host, i.e., the Router
                 Solicitation message, shall be discarded (if it
                 reaches the VLAN sub-interface).";
            }
            enum secured-host {
              description
                "Upstream ICMPv6 messages that can be sent by a host
                 are forwarded. Messages that can be sent only by a
                 router are discarded. Discarded messages are:
                 - Router Advertisement
                 - Redirect
                 - MLD query messages.

                 Downstream ICMPv6 messages that could reveal data of
                 one user to another shall be sent to the right user
                 only or shall be discarded. For example, the
                 multicast Neighbor Solicitation message sent to
                 resolve a user's IP address to a MAC address shall be
                 discarded.";
            }
          }
        }
        default "true";
        description
          "The ICMPv6 Relay will forward messages as defined by the
           selected enum value.";
        reference
          "TR-177 R-17;
           TR-177 R-18;
           TR-177 R-19;
           TR-177 R-20";
      }
      leaf unknown-type-processing {
        type enumeration {
          enum forward {
            description
              "ICMPv6 messages with a type unknown to the device are
               processed based on the layer 2 forwarding
               configuration.";
          }
          enum discard {
            description
              "ICMPv6 messages with a type unknown to the device are
               discarded.";
          }
        }
        default "forward";
        description
          "Manages how to process ICMPv6 messages with a type unknown
           to the device.";
        reference
          "TR-177 R-13";
      }
      leaf profile-ref {
        when "../enabled = 'true'" {
          description
            "Applicable only when ICMPv6 Relay functionality is
             enabled.";
        }
        if-feature "bbf-icmpv6-pc:relay-with-lio";
        type leafref {
          path "/bbf-icmpv6:icmpv6-profiles/bbf-icmpv6:"
             + "icmpv6-profile/bbf-icmpv6:name";
        }
        mandatory true;
        description
          "Reference to the ICMPv6 configuration profile.";
      }
    }
  }
}
