module bbf-eth-oam {
  yang-version 1.1;
  namespace "urn:bbf:yang:bbf-eth-oam";
  prefix bbf-eth-oam;

  import ieee802-dot1q-cfm {
    prefix dot1q-cfm;
  }

  organization
    "Broadband Forum <https://www.broadband-forum.org>
     Common YANG Work Area";
  contact
    "Comments or questions about this Broadband Forum YANG module
     should be directed to <mailto:help@broadband-forum.org>.

     Editor:      Shiya Ashraf, Nokia

     Editor:      Nick Hancock, Adtran

     Editor:      Kevin Noll, CableLabs

     Editor:      Ludwig Pauwels, Nokia

     PS Leader:   Aihua Guo, Futurewei

     WA Director: Joey Boyd, Adtran

     WA Director: Sven Ooghe, Nokia";
  description
    "This module is part of a collection of YANG definitions for
     supporting the Broadband Forum requirements on Connectivity Fault
     Management (CFM) Operations, Administration, and Maintenance
     (OAM) as applicable to access network equipment. As such, this
     module is specific to access network equipment (e.g., BBF-
     specified Access Nodes and FTTdp DPUs).

     Specifically, this module augments the IEEE 802.1Qcx CFM YANG
     data model with data nodes to support BBF-specific requirements
     relating to Ethernet OAM capabilities defined in ITU-T G.8013 and
     ITU-T G.8021.

     Copyright (c) 2017-2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a8; see
     the TR itself for full legal notices.";

  revision 2024-11-11 {
    description
      "Amendment 8.
       * Approval Date:    2024-11-11.
       * Publication Date: 2024-11-11.";
    reference
      "TR-383a8: Common YANG Modules for Access Networks
                 <https://www.broadband-forum.org/technical/download/
                          TR-383_Amendment-8.pdf>";
  }

  feature only-itut-oam-fm-supported {
    description
      "Indicates that only ITU-T Ethernet OAM FM state machines are
       supported on the server, i.e., IEEE 802.1Q CFM state machines
       are not supported on the server.";
  }

  augment "/dot1q-cfm:cfm/dot1q-cfm:maintenance-group" {
    if-feature "not only-itut-oam-fm-supported";
    description
      "Augments the Maintenance Group Broadband Forum specific
       configuration.";
    leaf itut-oam-fm-supported {
      type boolean;
      default "false";
      description
        "If 'true', the Maintenance Group implements ITU-T Ethernet
         OAM Fault Management (FM) state machines.

         If 'false' the Maintenance Group implements IEEE 802.1Q CFM
         state machines.";
      reference
        "ITU-T G.8013 Clause 7";
    }
  }
}
