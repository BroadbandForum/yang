module bbf-vlan-sub-interface-profile-dhcpv4 {
  yang-version 1.1;
  namespace "urn:bbf:yang:bbf-vlan-sub-interface-profile-dhcpv4";
  prefix bbf-vsi-prof-dhcpv4;

  import bbf-vlan-sub-interface-profiles {
    prefix bbf-vsi-prof;
  }
  import bbf-l2-dhcpv4-relay {
    prefix bbf-l2-d4r;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on the management of
     sub-interfaces as applicable to access network equipment. As
     such, this module is specific to access network equipment (e.g.,
     BBF-specified Access Nodes and FTTdp DPUs).

     Specifically, this module extends the VLAN sub-interface profile
     with DHCPv4 data nodes.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a6; see
     the TR itself for full legal notices.";

  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }

  feature replace-option-82 {
    description
      "Indicates support for accepting DHCPv4 messages that contain
       option 82 and forward the message after having replaced the
       option 82 with a new one generated by the device itself.";
  }

  augment "/bbf-vsi-prof:vsi-profiles"
        + "/bbf-vsi-prof:vsi-profile" {
    description
      "Augments the VLAN sub-interface profile with DHCPv4 data
       nodes.";
    container l2-dhcpv4-relay {
      presence
        "Enables support of L2 DHCPv4 Relay Agent functionality on
         interfaces referencing this profile.";
      description
        "L2 DHCPv4 Relay Agent configuration parameters.";
      leaf trusted-port {
        type union {
          type boolean;
          type enumeration {
            enum replace {
              if-feature "replace-option-82";
              description
                "For DHCPv4 messages containing option 82 information,
                 remove the existing option 82 information and replace
                 it based on the additional configuration for the L2
                 DHCPv4 Relay Agent.";
            }
          }
        }
        default "false";
        description
          "Affects the processing of DHCPv4 messages received on an
           interface and containing option 82.

           The value 'true' means messages containing option 82 are
           accepted and forwarded with option 82 unchanged. When the
           L2 DHCP Relay Agent receives in the downstream direction a
           reply containing option 82, which is a copy of the value
           that was passed in the upstream direction, then it does not
           remove this and sends the message on the interface with
           option 82 kept in.

           The value 'false' means the DHCPv4 messages containing
           option 82 shall be discarded.

           The value 'replace' means that the DHCPv4 message received
           on an interface will be modified before forwarding the
           message. The option 82 that is present in downstream
           messages, which is a copy of the one generated by the DHCP
           Relay Agent, shall be removed before sending the message on
           an interface.

           Does not affect the processing of DHCPv4 messages received
           on an interface without option 82.";
      }
      leaf profile-ref {
        type leafref {
          path "/bbf-l2-d4r:l2-dhcpv4-relay-profiles/bbf-l2-d4r:l2-"
             + "dhcpv4-relay-profile/bbf-l2-d4r:name";
        }
        mandatory true;
        description
          "Reference to the DHCPv4 configuration profile.

           Affects the processing of DHCPv4 messages received on an
           interface and not containing option 82. Option 82 shall be
           added before forwarding the message upstream. The content
           of option 82 is determined by the referenced profile. When
           option 82 is inserted in the upstream direction, then
           option 82 shall be removed from the downstream replies
           before sending the message on an interface.

           Also affects the processing of DHCPv4 messages received on
           an interface with option 82 when the leaf 'trusted-port' is
           set to 'replace'. In that case the option 82 received on an
           interface is removed and replaced by a newly generated one
           according the referenced profile.

           Does not affect the processing of DHCPv4 messages received
           on an interface with option 82 when the leaf 'trusted-port'
           does not exist or has a value different from 'replace'.";
      }
    }
  }
}
