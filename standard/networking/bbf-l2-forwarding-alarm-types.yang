module bbf-l2-forwarding-alarm-types {
  yang-version 1.1;
  namespace "urn:bbf:yang:bbf-l2-forwarding-alarm-types";
  prefix bbf-l2-fwd-alt;

  import bbf-alarm-types {
    prefix bbf-alt;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on layer 2 forwarding
     as applicable to access network equipment. As such, this module
     is specific to access network equipment (e.g., BBF-specified
     Access Nodes and FTTdp DPUs).

     Specifically, this module contains a set of alarm definitions
     related to the management of L2 forwarders.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }

  identity l2-forwarding-alarm-type-id {
    base bbf-alt:bbf-alarm-type-id;
    description
      "Base identity for defining Layer 2 Forwarding alarm identities.

       This identity is abstract and should not generally be used for
       alarms. If used to define an alarm that was not known at
       design time, it must be qualified with an alarm type qualifier
       string. This practice, however, should be generally avoided to
       ensure all possible alarms are known at design time.";
  }

  identity l2-forwarding-duplicate-mac-learning {
    base l2-forwarding-alarm-type-id;
    description
      "A 'l2-forwarding-duplicate-mac-learning' alarm is declared when
       a frame is received that triggers a MAC learning process on a
       port/interface for a source MAC address that was already
       learned on different port/interface, and MAC movement rules
       forbid the movement of the MAC address from the original
       port/interface to the port/interface where the frame is
       received.

       Raising this alarm causes the system to take protective
       measures. At a minimum, the system will deny further MAC
       learning attempts from other frames with the same source MAC
       address on the same port/interface during a system-defined
       time.

       The alarm is cleared when the system-defined time for taking
       the protective measures expires, or in case operator actions
       removed the offended MAC address from the forwarding database,
       creating the conditions to learn the MAC address again on a
       port/interface.";
  }

  identity system-maximum-mac-addresses-exceeded {
    base l2-forwarding-alarm-type-id;
    description
      "A 'system-maximum-mac-addresses-exceeded' alarm is declared
       when no resources are available in the system for dynamically
       learning a MAC address.

       The alarm is cleared when at least one resource is again
       available for a system-defined time.";
  }
}
