module bbf-dot1q-cfm-interfaces {
  yang-version 1.1;
  namespace "urn:bbf:yang:bbf-dot1q-cfm-interfaces";
  prefix bbf-cfm-if;

  import iana-if-type {
    prefix ianaift;
  }
  import ietf-interfaces {
    prefix if;
  }
  import bbf-if-type {
    prefix bbfift;
  }
  import ieee802-dot1q-cfm {
    prefix dot1q-cfm;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     WA Director: Joey Boyd, ADTRAN

     WA Director: Sven Ooghe, Nokia";
  description
    "This module is part of a collection of YANG definitions for
     supporting the Broadband Forum requirements on Connectivity Fault
     Management (CFM) Operations, Administration, and Maintenance
     (OAM) as applicable to access network equipment. As such, this
     module is specific to access network equipment (e.g., BBF-
     specified Access Nodes and FTTdp DPUs).

     Specifically, this module augments the IEEE 802.1Qcx CFM YANG
     data model to link a Maintenance Association (MA) End Point (MEP)
     to an interface.

     Copyright (c) 2017-2022, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a5; see
     the TR itself for full legal notices.";

  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }

  augment "/dot1q-cfm:cfm/dot1q-cfm:maintenance-group/dot1q-cfm:mep" {
    description
      "Augment a MEP with BBF specific data nodes.";
    leaf interface {
      type if:interface-ref;
      must
        "derived-from-or-self(/if:interfaces/if:interface"
      + "[if:name = current()]/if:type,'bbfift:vlan-sub-interface') "
      + "or ((derived-from(/if:interfaces/if:interface"
      + "[if:name = current()]/if:type,'bbfift:ethernet-like') or "
      + "derived-from-or-self(/if:interfaces/if:interface"
      + "[if:name = current()]/if:type,'ianaift:ptm') or "
      + "derived-from-or-self(/if:interfaces/if:interface"
      + "[if:name = current()]/if:type,'ianaift:ethernetCsmacd')) "
      + "and current()/../dot1q-cfm:direction = 'down')" {
        error-message
          "Only down-MEPs can be created on an Ethernet-like "
        + "interface.";
        description
          "Ethernet-like interfaces are interfaces that have a type
           that specializes the abstract type 'bbfift:ethernet-like',
           or use or specialize the types'ianaift:ptm' or
           'ianaift:ethernetCsmacd'.

           On such interfaces only down-MEPs can be created.

           On top of any of these interfaces VLAN sub-interfaces can
           be created. On VLAN sub-interfaces both up- and down-MEPs
           can be created.";
      }
      must
        'count(current()/../../dot1q-cfm:mep[bbf-cfm-if:interface'
      + ' = current()]) <= 1' {
        error-message
          "Two MEPs can not coexist on the same interface within the "
        + "same Maintenance Group.";
        description
          "Ensure that the number of MEPs within the Maintenance Group
           linked to the interface is less than or equal to 1, because
           within a single Maintenance Group it is not permitted to
           configure two MEPs on the same interface.";
      }
      description
        "References the interface on which the MEP shall be created.
         Note that MEPs can be VLAN-unaware and refer to a link-level
         interface or can be VLAN-aware and refer to a VLAN
         sub-interface. Note that a Link Aggregation Group (LAG) would
         not be a link-level interface. This is because IEEE 802.1ag
         defines that if a LAG is used in combination with
         VLAN-unaware MEPs, then the MEPs are configured below the
         LAG, i.e. per Ethernet interface.

         The following is a relevant constraint not written in YANG:
         All up-MEPs within a single MA shall reference VLAN
         sub-interfaces that participate in the same forwarder.";
    }
  }
}
