module bbf-alarm-types {
  yang-version 1.1;
  namespace "urn:bbf:yang:bbf-alarm-types";
  prefix bbf-alt;

  import ietf-alarms {
    prefix al;
  }

  organization
    "Broadband Forum <https://www.broadband-forum.org>
     Provider Cloud Work Area";
  contact
    "Comments or questions about this Broadband Forum YANG module
     should be directed to <mailto:info@broadband-forum.org>.

     Editor:      Shiya Ashraf, Nokia

     Editor:      Kevin Noll, CableLabs

     PS Leader:   Sven Ooghe, Nokia

     PS Leader:   Joey Boyd, Adtran

     WA Director: Bruno Cornaglia, Vodafone

     WA Director: Mengmeng Li, China Mobile

     WA Director: Haomian Zheng, Huawei";
  description
    "This module contains a collection of YANG definitions for
     supporting the Broadband Forum requirements on the management
     of alarms as applicable to access network equipment. As such,
     this module is specific to access network equipment (e.g.,
     BBF-specified Access Nodes and FTTdp DPUs).

     Specifically, this module defines abstract alarm types that are
     needed for BBF applications to be able to define their own
     specific abstract and concrete alarm types.

     Copyright (c) 2017-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a9; see
     the TR itself for full legal notices.";

  revision 2025-07-02 {
    description
      "Amendment 9.
       * Approval Date:    2025-07-02.
       * Publication Date: 2025-07-02.";
    reference
      "TR-383a9: Common YANG Modules for Access Networks
                 <https://www.broadband-forum.org/technical/download/
                          TR-383_Amendment-9.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }

  identity bbf-alarm-type-id {
    base al:alarm-type-id;
    description
      "Base identity for all alarm type identifiers defined in
       BBF YANG modules. The base identity represents the commonality
       of all BBF alarms and implicitly defines a set of alarm
       information that may be associated with all alarms based on
       this identity. See TR-383 for more details.

       A specific BBF YANG module may define its own base identities,
       but they must be derived from this identity directly or from
       another identity derived from this identity.

       This identity is abstract and should not generally be used for
       alarms. If used to define an alarm that was not known at
       design time, it must be qualified with an alarm type qualifier
       string. This practice, however, should be generally avoided to
       ensure all possible alarms are known at design time.";
    reference
      "TR-383a3";
  }

  identity bbf-security-alarm-type-id {
    base bbf-alarm-type-id;
    description
      "Base identity for all alarm type identifiers that represent
       security alarms defined in BBF YANG modules. This base identity
       implicitly defines a set of additional security-specific alarm
       information to that associated with 'bbf-alarm-type-id' that
       may be provided by all alarms based on this identity. See
       TR-383 for more details.

       A specific BBF YANG module may define its own base identities
       for security alarms, but they must be derived from this
       identity directly or from another identity derived from this
       identity.

       This identity is abstract and should not generally be used for
       alarms. If used to define an alarm that was not known at
       design time, it must be qualified with an alarm type qualifier
       string. This practice, however, should be generally avoided to
       ensure all possible alarms are known at design time.";
    reference
      "ITU-T X.736";
  }

  identity bbf-threshold-crossing-alarm-type-id {
    base bbf-alarm-type-id;
    description
      "Base identity for all alarm type identifiers that represent
       threshold crossing alarms defined in BBF YANG modules. This
       base identity implicitly defines a set of additional threshold
       crossing alarm information to that associated with
       'bbf-alarm-type-id' that may be provided by all alarms based
       on this identity. See TR-383 for more details.

       A specific BBF YANG module may define its own base identities
       for threshold crossing alarms, but they must be derived from
       this identity directly or from another identity derived from
       this identity.

       This identity is abstract and should not generally be used for
       alarms. If used to define an alarm that was not known at
       design time, it must be qualified with an alarm type qualifier
       string. This practice, however, should be generally avoided to
       ensure all possible alarms are known at design time.";
    reference
      "ITU-T X.733 clause 8.1.2.7";
  }
}
