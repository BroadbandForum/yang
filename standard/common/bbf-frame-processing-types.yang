module bbf-frame-processing-types {
  yang-version 1.1;
  namespace "urn:bbf:yang:bbf-frame-processing-types";
  prefix bbf-fpt;

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on reusable data
     types as applicable to access network equipment. As such, this
     module is specific to access network equipment (e.g.,
     BBF-specified Access Nodes and FTTdp DPUs).

     Specifically, this module defines common types used throughout
     the modeling of frame processing.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a6; see
     the TR itself for full legal notices.";

  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }

  typedef tag-index {
    type uint8 {
      range "0..1";
    }
    description
      "The index of the VLAN tag in a frame or in a piece of metadata.

       When used as index of a VLAN tag in a frame, then:
       - Tag 0 refers to the outer tag, i.e., the tag just after the
       source MAC address.
       - Tag 1 refers to the tag after tag 0.

       Metadata is data that belongs to the frame but is not a field
       of the frame itself. It is also a list that is indexed using a
       tag-index. Once assigned to the frame it travels with the frame
       until the frame is transmitted or discarded, and this is
       independent of all frame manipulations that take place. The
       content of this metadata is generated via a QoS profile or via
       a copy from the frame's field in a VLAN sub-interface ingress
       rewrite. Note that a frame has just one p-bits marking list,
       i.e., if multiple actions write to the same position in the
       list, then the last write overwrites the previous.

       As an example, it is possible to provide a metadata pbit to a
       frame at the ingress side, this data travels with the frame
       through the switch, and the metadata is used at the egress side
       when a VLAN tag is pushed into the frame.";
  }

  typedef qos-pbit-marking-index {
    type uint8;
    description
      "An index to a Priority Code Point bits (p-bits) marking list.

       The marking list is a piece of metadata, i.e., it is data that
       belongs to the frame but is not a field of the frame itself.
       Once assigned to the frame it travels with the frame until the
       frame is transmitted or discarded, and this is independent of
       all frame manipulations that take place. The content of this
       marking list is generated via a QoS profile or via a copy from
       the frame's pbit in a VLAN sub-interface ingress rewrite. Note
       that a frame has just one p-bits marking list, i.e., if
       multiple actions write to the same position in the list, then
       the last write overwrites the previous.

       As an example, it is possible to provide a metadata pbit to a
       frame at the ingress side, this data travels with the frame
       through the switch, and the metadata is used at the egress side
       when a VLAN tag is pushed into the frame.";
  }

  typedef qos-dei-marking-index {
    type uint8;
    description
      "An index to a Drop Eligibility Indicator (DEI) marking list.

       The marking list is a piece of metadata, i.e., it is data that
       belongs to the frame but is not a field of the frame itself.
       Once assigned to the frame it travels with the frame until the
       frame is transmitted or discarded, this independent of all
       frame manipulations that take place. The content of this
       marking list is generated via a QoS profile or via a copy from
       the frame's DEI in a VLAN sub-interface ingress rewrite. Note
       that a frame has just one DEI marking list, i.e., if multiple
       actions write to the same position in the list, then the last
       write overwrites the previous.

       As an example, it is possible to provide a metadata DEI to a
       frame at the ingress side, this data travels with the frame
       through the switch, and the metadata is used at the egress side
       when a VLAN tag is pushed into the frame.";
  }
}
