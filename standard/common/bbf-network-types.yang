module bbf-network-types {
  yang-version 1.1;
  namespace "urn:bbf:yang:bbf-network-types";
  prefix bbf-ntwrkt;

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Broadband Forum requirements on providing
     network information associated with network functions.

     Specifically, this module defines common types associated with
     network information.

     This module contains a collection of YANG definitions for
     types associated with BBF network information.

     Copyright (c) 2017-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a4; see
     the TR itself for full legal notices.";

  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }

  // Identities
  // Deployment Types

  identity deployment-type {
    description
      "Base identity from which specific network deployment types are
       derived.";
  }

  identity access-deployment-type {
    base deployment-type;
    description
      "Derived identity for access network specific deployment
       types.";
  }

  identity fttx-type {
    base access-deployment-type;
    description
      "Derived identity from which specific access fttx types are
       derived.";
  }

  identity ftth {
    base fttx-type;
    description
      "Fiber to the home.";
  }

  identity fttdp {
    base fttx-type;
    description
      "Fiber to the distribution point.";
  }

  identity fttb {
    base fttx-type;
    description
      "Fiber to the building.";
  }

  identity fttcab {
    base fttx-type;
    description
      "Fiber to the cabinet.";
  }

  identity ftte {
    base fttx-type;
    description
      "Fiber to the equipment.";
  }

  // Network Distribution Frame Types

  identity distribution-frame-type {
    description
      "Base identity from which specific distribution frame types are
       derived.";
  }

  identity copper-distribution-frame {
    base distribution-frame-type;
    description
      "The copper distribution frame.";
  }

  identity optical-distribution-frame {
    base distribution-frame-type;
    description
      "The optical distribution frame.";
  }
}
