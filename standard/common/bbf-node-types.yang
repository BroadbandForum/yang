module bbf-node-types {
  yang-version 1.1;
  namespace "urn:bbf:yang:bbf-node-types";
  prefix bbf-nodet;

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Broadband Forum requirements on providing
     network node information associated with network functions.

     Specifically, this module defines common types associated with
     network nodes.

     This module contains a collection of YANG definitions for
     types associated with BBF network nodes.

     Copyright (c) 2017-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a4; see
     the TR itself for full legal notices.";

  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }

  //Identities
  // Node types

  identity node-type {
    description
      "Base identity from which specific node types are derived.";
  }

  identity network-device {
    base node-type;
    description
      "A physical network device type of node.";
  }

  identity end-user-device {
    base node-type;
    description
      "An end-user device type of node.";
  }

  // Software types

  identity software-type {
    description
      "Base identity from which the purpose of the software is
       derived.";
  }

  identity software {
    base software-type;
    description
      "Software is for the purpose of the element's general
       software.";
  }

  identity firmware {
    base software-type;
    description
      "Software is for the purpose of the element's firmware.";
  }

  identity baa-device-adapter {
    base software-type;
    description
      "Software is for the purpose of the Broadband Access Abstraction
       (BAA) layer device adapter.";
  }

  //Typedefs
  // Node alignment state

  typedef alignment-state {
    type enumeration {
      enum not-aligned {
        description
          "The node is unaligned with the underlying resources that
           the node represents.";
      }
      enum aligned {
        description
          "The node is aligned with the underlying resources that the
           node represents.";
      }
    }
    description
      "The alignment state between the view of a node in a management
       system and the actual configuration in the managed node
       itself.";
  }

  // Node administrative state

  typedef admin-state {
    type enumeration {
      enum unknown {
        description
          "The resource is unable to report administrative state.";
      }
      enum locked {
        description
          "The resource is administratively prohibited from use.";
      }
      enum shutting-down {
        description
          "The resource usage is administratively limited to current
           instances of use.";
      }
      enum unlocked {
        description
          "The resource is not administratively prohibited from use.";
      }
    }
    description
      "The administrative state of the node for maintenance
       purposes.";
  }
}
