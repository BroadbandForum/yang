module bbf-device-types {
  yang-version 1.1;
  namespace "urn:bbf:yang:bbf-device-types";
  prefix bbf-dvct;

  organization
    "Broadband Forum <https://www.broadband-forum.org>
     Provider Cloud Work Area";
  contact
    "Comments or questions about this Broadband Forum YANG module
     should be directed to <mailto:info@broadband-forum.org>.

     Editor:      Shiya Ashraf, Nokia

     PS Leader:   Sven Ooghe, Nokia

     PS Leader:   Joey Boyd, Adtran

     WA Director: Bruno Cornaglia, Vodafone

     WA Director: Aihua Guo, Futurewei";
  description
    "This module contains a collection of YANG definitions for
     supporting the Broadband Forum requirements on managing physical
     devices.

     Specifically, this module defines common types associated with
     device management.

     Copyright (c) 2017-2026, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a10; see
     the TR itself for full legal notices.";

  revision 2026-07-02 {
    description
      "Amendment 10.
       * Approval Date:    2026-07-02.
       * Publication Date: 2026-07-02.";
    reference
      "TR-383a10: Common YANG Modules for Access Networks
                  <https://www.broadband-forum.org/technical/download/
                           TR-383_Amendment-10.pdf>";
  }
  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }

  // Identities
  // Device types

  identity device-type {
    description
      "Base identity from which specific device node types are
       derived.";
  }

  identity access-device-type {
    base device-type;
    description
      "Base identity from which specific access device node types are
       derived.";
  }

  identity dpu {
    base access-device-type;
    description
      "Distribution Point Unit (DPU).";
  }

  identity msan {
    base access-device-type;
    description
      "Multiservice Access Node (MSAN).";
  }

  identity dslam {
    base access-device-type;
    description
      "Digital Subscriber Line Access Multiplexer (DSLAM).";
  }

  identity olt {
    base access-device-type;
    description
      "Optical Line Terminal (OLT).";
  }

  identity onu {
    base access-device-type;
    description
      "Optical Network Unit (ONU).";
  }

  identity fast-cpe {
    base access-device-type;
    description
      "The G.fast CPE. G.fast is a Digital Subscriber Line (DSL)
       protocol standard.";
  }

  identity vdsl2-cpe {
    base access-device-type;
    description
      "The Very High-speed Digital Subscriber Line 2 (VDSL2) CPE.";
  }

  identity splitter {
    base access-device-type;
    description
      "An optical splitter, which typically has an a-port and several
       z-ports.";
  }

  identity subscriber-demarcation-point {
    base access-device-type;
    description
      "A subscriber demarcation point usually in the form factor of a
       box typically installed outside the house, and provides a
       testing and flexibility point as well as storage for cable
       slack.";
  }

  identity coexistence-element {
    base access-device-type;
    description
      "A coexistence element is a passive device that allows to
       multiplex two or more xPON technologies/services transported
       together on the same fiber by using wavelength division
       multiplexing (WDM) technologies (filters) to overlay the
       different wavelengths of the multiple services.";
  }

  identity odf {
    base access-device-type;
    description
      "An Optical Distribution Frame. The ODF acts as a central hub
       in a PON's infrastructure, where fiber optic cables from an
       OLT are terminated, and cross-connected to splitters or other
       components of the Optical Distribution Network.";
  }

  // Device Subcategory

  identity device-subcategory {
    description
      "Base identity from which specific subcategories of device types
       are derived.";
  }

  identity access-device-subcategory {
    base device-subcategory;
    description
      "Identity from which specific subcategories of access device
       types are derived.";
  }

  identity multi-card {
    base access-device-subcategory;
    description
      "The multi card subcategory.

       An access device of this or a derived identity is a device that
       has the capability to support multiple cards, independent of
       the actual deployment.";
  }

  identity single-card {
    base access-device-subcategory;
    description
      "The single card subcategory.

       An access device of this or a derived identity is a device that
       is a fully self-contained device that does not has the
       capability to plug or unplug cards.";
  }

  identity pluggable-transceiver {
    base access-device-subcategory;
    description
      "The pluggable transceiver subcategory.";
  }
}
