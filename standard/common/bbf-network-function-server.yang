module bbf-network-function-server {
  yang-version 1.1;
  namespace "urn:bbf:yang:bbf-network-function-server";
  prefix bbf-nfs;

  import bbf-yang-types {
    prefix bbf-yang;
  }
  import ietf-yang-types {
    prefix yang;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on network functions
     as applicable to access network equipment. As such, this module
     is specific to access network equipment (e.g., BBF-specified
     Access Nodes and FTTdp DPUs).

     Specifically, this module defines a set of common groupings to
     support server endpoints of network connections between network
     functions.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2022-06-07 {
    description
      "Issue 1.
       * Approval Date:    2022-06-07.
       * Publication Date: 2022-06-07.";
    reference
      "TR-451: vOMCI Specification
               <https://www.broadband-forum.org/technical/download/
                        TR-451_Issue-1.pdf>";
  }

  grouping nf-server {
    description
      "Data nodes to manage incoming connections to network functions,
       i.e., when acting as a server to a remote client.";
    container listen {
      presence "Enables server to listen for client connections.";
      description
        "Configures listen behavior.";
      leaf idle-timeout {
        type uint16;
        units "seconds";
        default "3600";
        description
          "The maximum number of seconds that a gRPC channel may have
           no outstanding RPCs, after which the server will close the
           connection.

           If set to zero, then the server is not to close the
           connection, if it is idle.

           Note that connections for which sessions have a
           notification subscription active are never closed.";
      }
      list listen-endpoint {
        key "name";
        min-elements 1;
        description
          "An endpoint to listen for connections.";
        leaf name {
          type bbf-yang:string-ascii64;
          description
            "An arbitrary name for the listen endpoint.";
        }
        leaf local-service-endpoint {
          type bbf-yang:string-ascii64;
          description
            "The service endpoint name the NF is to use to identify
             this listen endpoint when a remote endpoint attempts to
             establish a session to it.";
        }
        choice transport {
          mandatory true;
          description
            "Selects between available transports.";
        }
        container remote-clients {
          config false;
          description
            "Remote clients that are currently connected to the
             server.";
          list remote-client {
            key "local-service-endpoint";
            description
              "A remote client that is currently connected.";
            leaf local-service-endpoint {
              type bbf-yang:string-ascii64;
              description
                "Identity of the local service endpoint of the remote
                 endpoint as provided as part of the vOMCI hello
                 exchange when the connection to the remote endpoint
                 was established.";
            }
          }
          notification remote-client-status-change {
            description
              "A notification traceable to a server listen endpoint
               and a remote endpoint associated with the listen
               endpoint. This notification is sent when remote
               endpoint is connected or disconnected to/from the
               listen endpoint.";
            leaf remote-client {
              type leafref {
                path "../../remote-client/local-service-endpoint";
                require-instance false;
              }
              mandatory true;
              description
                "The remote endpoint that was connected or
                 disconnected.";
            }
            leaf connected {
              type boolean;
              mandatory true;
              description
                "If 'true', the remote endpoint was connected.

                 If 'false', the remote endpoint was disconnected.";
            }
            leaf remote-endpoint-state-last-change {
              type yang:date-and-time;
              mandatory true;
              description
                "The system date and time when the remote endpoint was
                 connected or disconnected.";
            }
          }
        }
      }
    }
  }
}
