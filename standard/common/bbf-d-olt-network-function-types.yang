module bbf-d-olt-network-function-types {
  yang-version 1.1;
  namespace "urn:bbf:yang:bbf-d-olt-network-function-types";
  prefix bbf-d-olt-nft;

  import bbf-network-function-types {
    prefix bbf-nft;
  }

  organization
    "Broadband Forum <https://www.broadband-forum.org>
     SDN/NFV Work Area";
  contact
    "Comments or questions about this Broadband Forum YANG module
     should be directed to <mailto:help@broadband-forum.org>.

     Editor:      Andre Brizido, Altice Labs

     Editor:      Antonio Marsico, Reply

     PS Leader:   Haomian Zheng, Huawei

     WA Director: Mengmeng Li, China Mobile

     WA Director: Bruno Cornaglia, Vodafone";
  description
    "This module contains a collection of YANG definitions
     for common types supporting the Broadband Forum requirements
     for the network functions associated with the Disaggregated
     OLT (D-OLT).

     Copyright (c) 2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-477; see
     the TR itself for full legal notices.";

  revision 2024-01-19 {
    description
      "Issue 1.
       * Approval Date:    2024-01-19.
       * Publication Date: 2024-01-19.";
    reference
      "TR-477: Cloud CO Enhancement - Access Node Functional
               Disaggregation <https://www.broadband-forum.org/
                               technical/download/TR-477.pdf>";
  }

  identity d-olt-dhcpra {
    base bbf-nft:access-vnf-type;
    description
      "DHCP Relay Agent (DHCPRA) network
       function for the D-OLT";
  }

  identity d-olt-pppoeia {
    base bbf-nft:access-vnf-type;
    description
      "PPPoE Intermediate Agent (PPPoEIA)
       network function for the D-OLT";
  }

  identity d-olt-mgmd {
    base bbf-nft:access-vnf-type;
    description
      "MGMD network function for the D-OLT";
  }

  identity d-olt-onuauth {
    base bbf-nft:access-vnf-type;
    description
      "ONU authentication network function
       for the D-OLT";
  }

  identity d-olt-vdba {
    base bbf-nft:access-vnf-type;
    description
      "Virtual Dynamic Bandwidth Allocation (vDBA)
       network function for the D-OLT.";
  }

  identity d-olt-mfc {
    description
      "One of the Management Flow Control (Mfc) interfaces";
  }

  identity mfc-sci {
    base d-olt-mfc;
    description
      "Management flow control State Control
       interface (Mfc_SCi)";
  }

  identity mfc-cpri {
    base d-olt-mfc;
    description
      "Management flow control Control Protocol
       Redirect interface (Mfc_CPRi)";
  }
}
