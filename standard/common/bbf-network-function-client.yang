module bbf-network-function-client {
  yang-version 1.1;
  namespace "urn:bbf:yang:bbf-network-function-client";
  prefix bbf-nfc;

  import bbf-network-function-types {
    prefix bbf-nft;
  }
  import bbf-yang-types {
    prefix bbf-yang;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on network functions
     as applicable to access network equipment. As such, this module
     is specific to access network equipment (e.g., BBF-specified
     Access Nodes and FTTdp DPUs).

     Specifically, this module defines a set of common groupings to
     support client endpoints of network connections between network
     functions.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2022-06-07 {
    description
      "Issue 1.
       * Approval Date:    2022-06-07.
       * Publication Date: 2022-06-07.";
    reference
      "TR-451: vOMCI Specification
               <https://www.broadband-forum.org/technical/download/
                        TR-451_Issue-1.pdf>";
  }

  grouping nf-client {
    description
      "Data nodes to manage outgoing connections to network functions,
       i.e., when acting as a client to a remote server.";
    container initiate {
      description
        "Configures connections the client is to initiate.

         If multiple remote servers are configured, they are handled
         independently.";
      list remote-server {
        key "name";
        description
          "A remote server the client is to connect to.";
        leaf name {
          type bbf-yang:string-ascii64;
          description
            "An arbitrary name for the remote server.";
        }
        leaf nf-type {
          type identityref {
            base bbf-nft:nf-type;
          }
          description
            "The type of network function associated with the remote
             endpoint (e.g, vOMCI-proxy, vOMCI-function, vOLTMF, OLT).

             This may be used to verify whether the endpoint when
             connected is of the appropriate type.";
        }
        leaf on-demand {
          type boolean;
          default "false";
          description
            "Determines whether the client is to establish a
             connection to the endpoint only on-demand ('true'),
             i.e., only when and if the connection is needed, or
             whether the client is to establish a persistent
             connection ('false').";
        }
        leaf local-service-endpoint {
          type bbf-yang:string-ascii64;
          description
            "The service endpoint name the NF is to use to identify
             this endpoint when establishing a session to the remote
             endpoint.";
        }
        choice transport {
          mandatory true;
          description
            "Selects between available client transports.";
        }
      }
    }
  }
}
