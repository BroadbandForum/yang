module bbf-network-function {
  yang-version 1.1;
  namespace "urn:bbf:yang:bbf-network-function";
  prefix bbf-nf;

  import bbf-network-function-types {
    prefix bbf-nft;
  }
  import bbf-yang-types {
    prefix bbf-yang;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on network functions
     as applicable to access network equipment. As such, this module
     is specific to access network equipment (e.g., BBF-specified
     Access Nodes and FTTdp DPUs).

     Specifically, this module defines a set of common groupings to
     support the topology of network functions within a network. For
     example, use-cases such as Disaggregated OLT or Virtual OMCI,
     which use cloud-based network functions via network connectivity,
     use this module as the basis for adding additional clients and
     servers for that network connectivity. The specific endpoints,
     protocols, and transport features are described within their
     respective documents and modules.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2022-06-07 {
    description
      "Issue 1.
       * Approval Date:    2022-06-07.
       * Publication Date: 2022-06-07.";
    reference
      "TR-451: vOMCI Specification
               <https://www.broadband-forum.org/technical/download/
                        TR-451_Issue-1.pdf>";
  }

  grouping topology-type {
    description
      "Data nodes that define a type of topology in which a network
       function operates.";
    leaf type {
      type identityref {
        base bbf-nft:nf-topology;
      }
      description
        "The type of deployment topology.";
    }
    leaf other-type {
      when "derived-from-or-self(../type,"
         + "'bbf-nft:other-topology')" {
        description
          "Only valid when the topology type is 'other-topology'.";
      }
      type bbf-yang:string-ascii64;
      description
        "The other type of deployment topology used, if 'type' is set
         to 'other-topology'.";
    }
  }

  grouping vnf {
    description
      "Data nodes describing the VNF 'flavor' (not instance) being
       used. For example, vendor or version info.";
    leaf vendor {
      type bbf-yang:string-ascii64;
      description
        "The vendor of the VNF.";
    }
    leaf software-version {
      type bbf-yang:string-ascii64;
      description
        "The software version of VNF.";
    }
    leaf nf-type {
      type identityref {
        base bbf-nft:vnf-type;
      }
      mandatory true;
      description
        "The type of the VNF within the solution context.
         For example: 'onu-management-proxy', 'vomci-function',
         'vomci-proxy'.";
    }
  }

  grouping nf-topology {
    description
      "Data nodes that define a configured (intended) network
       function topology.";
    uses topology-type;
    list vnf {
      key "name";
      description
        "A 'flavor' of VNF (not instance) intended to be used within
         the network. For example, 'flavor' can be based on vendor or
         version info.";
      leaf name {
        type bbf-yang:string-ascii64;
        description
          "The name of the 'flavor' of VNF.";
      }
      uses bbf-nf:vnf;
    }
    list vnf-instance {
      key "name";
      description
        "An instance of a VNF.";
      leaf name {
        type bbf-yang:string-ascii64;
        description
          "The name of the VNF instance.";
      }
      leaf vnf {
        type leafref {
          path "../../vnf/name";
        }
        mandatory true;
        description
          "The name of the 'flavor' of VNF intended to be used within
           the network.";
      }
    }
    list nf-link {
      key "name";
      description
        "An intended link between network functions within the
         network. Depending on usage, endpoints of a link may be at a
         physical and/or a virtual NF.";
      leaf name {
        type bbf-yang:string-ascii64;
        description
          "The name of the link.";
      }
      list endpoint {
        key "nf-instance endpoint";
        max-elements 2;
        description
          "A service endpoint at an instance of a network function
           forming one end of a link between network functions.";
        leaf nf-instance {
          type bbf-yang:string-ascii64;
          description
            "The name of the instance of the network function.

             If the function is a PNF, then this value is the device
             identifier of the PNF.";
        }
        leaf endpoint {
          type bbf-yang:string-ascii64;
          description
            "The name of the service endpoint at the instance of the
             network function.";
        }
        leaf nf-type {
          type bbf-yang:string-ascii64;
          description
            "The type of network function.";
        }
      }
    }
  }

  grouping discovered-nf-topology {
    description
      "Data nodes that define a 'discovered' (operational) network
       function topology.

       Note this grouping is intended to be located in state data
       only.";
    uses topology-type;
    list vnf {
      key "name";
      description
        "A 'flavor' of VNF (not instance) discovered within the
         network.";
      leaf name {
        type bbf-yang:string-ascii64;
        description
          "The name of the 'flavor' of VNF.";
      }
      uses bbf-nf:vnf;
    }
    list vnf-instance {
      key "name";
      description
        "A discovered instance of a VNF.";
      leaf name {
        type bbf-yang:string-ascii64;
        description
          "The name of the VNF instance.";
      }
      leaf vnf {
        type leafref {
          path "../../vnf/name";
          require-instance false;
        }
        mandatory true;
        description
          "The name of the 'flavor' of VNF.";
      }
    }
    list nf-link {
      key "name";
      description
        "A discovered link between network functions.";
      leaf name {
        type bbf-yang:string-ascii64;
        description
          "The name of the link.";
      }
      list endpoint {
        key "nf-instance endpoint";
        max-elements 2;
        description
          "A discovered endpoint at an instance of a network function
           forming one end of a link.";
        leaf nf-instance {
          type bbf-yang:string-ascii64;
          description
            "The name of the instance of the network function at one
             end of the link.

             If the function is a PNF, then this value is the device
             identifier of the PNF.";
        }
        leaf endpoint {
          type bbf-yang:string-ascii64;
          description
            "The name of the endpoint at the instance of the network
             function.";
        }
        leaf nf-type {
          type bbf-yang:string-ascii64;
          description
            "The type of the network function.";
        }
      }
    }
  }
}
