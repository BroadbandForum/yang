module bbf-quality-attenuation-gsv {
  yang-version 1.1;
  namespace "urn:bbf:yang:bbf-quality-attenuation-gsv";
  prefix bbf-qattn-gsv;

  import bbf-t-digest {
    prefix bbf-t-digest;
  }

  organization
    "Broadband Forum <https://www.broadband-forum.org>
     Network Architecture Work Area";
  contact
    "Comments or questions about this Broadband Forum YANG module
     should be directed to <mailto:info@broadband-forum.org>.

     Editor:      Bjoern Ivar Teigen, CUJO AI

     PS Leader:   Xueyan Song, ZTE

     WA Director: Jonathan Newton, Vodafone

     WA Director: Christele Bouchat, Nokia";
  description
    "This module contains a collection of YANG definitions for
     supporting the Broadband Forum requirements on
     Quality Attenuation.

     Specifically, this module provides data nodes for
     the aggregation of Quality Attenuation data decomposed
     into G, S and V components.

     Copyright (c) 2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-452.4; see
     the TR itself for full legal notices.";

  revision 2025-09-09 {
    description
      "Issue 1.
       * Approval Date:    2025-09-09.
       * Publication Date: 2025-09-09.";
    reference
      "TR-452.4: QED Measurement Formats
                 <https://www.broadband-forum.org/technical/download/
                          TR-452.4.pdf>";
  }

  container gsv {
    description
      "Aggregated Quality Attenuation data decomposed into G, S and
       V components.";
    leaf g {
      type decimal64 {
        fraction-digits 12;
        range "0..max";
      }
      units "seconds";
      description
        "The value of the G component in the set of data. The
         maximum representable delay is approximately 224 days. The
         value of G should always be greater than or equal to 0
         because negative values must represent measurement error.";
    }
    leaf s {
      type decimal64 {
        fraction-digits 12;
      }
      units "seconds";
      description
        "The minimum value in the set of data. The maximum
         representable delay is approximately 224 days.";
    }
    leaf v-singleton {
      when 'not(../use-t-digest)';
      type decimal64 {
        fraction-digits 12;
        range "0..max";
      }
      units "seconds";
      description
        "The value of the V component in the set of data. The
         maximum representable delay is approximately 224 days. The
         value should always be greater than or equal to 0 because
         negative values must represent measurement error.";
    }
    leaf use-t-digest {
      type boolean;
      default "false";
      description
        "If 'true', the t-digest data structure should be used to
         represent the V component.";
    }
    container v-t-digest {
      when '../use-t-digest';
      uses bbf-t-digest:t-digest;
      description
        "A t-digest data structure for efficient approximate
         quantile calculation on the set of data.";
    }
  }
}
