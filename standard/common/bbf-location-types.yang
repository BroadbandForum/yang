module bbf-location-types {
  yang-version 1.1;
  namespace "urn:bbf:yang:bbf-location-types";
  prefix bbf-loct;

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on providing
     location information associated with network functions.

     Specifically, this module defines common types associated with
     location information.

     This module contains a collection of YANG definitions for
     types associated with BBF location information.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }

  // Identities

  identity site-type {
    description
      "Base identity from which specific site types are derived.";
  }

  identity central-office {
    base site-type;
    description
      "The type of site is a Central Office site.";
  }

  identity cabinet {
    base site-type;
    description
      "The type of site is a cabinet.";
  }

  identity basement {
    base site-type;
    description
      "The type of site is a basement of a building.";
  }

  identity floor {
    base site-type;
    description
      "The type of site is a floor of building.";
  }

  identity plant-type {
    description
      "Base identity from which specific plant types are derived. A
       plant is the place where the resource is located.";
  }

  identity indoor {
    base plant-type;
    description
      "The location of the resource is indoor.";
  }

  identity outdoor {
    base plant-type;
    description
      "The location of the resource is outdoor.";
  }

  identity manhole {
    base plant-type;
    description
      "The location of the resource is in a manhole.";
  }

  identity outdoor-cabinet {
    base plant-type;
    description
      "The location of the resource in an outdoor cabinet.";
  }

  identity pole {
    base plant-type;
    description
      "The location of the resource is on a pole.";
  }

  identity building-facade {
    base plant-type;
    description
      "The location of the resource is on the building facade.";
  }

  identity pedestal {
    base plant-type;
    description
      "The location of the resource is within a pedestal.";
  }
}
